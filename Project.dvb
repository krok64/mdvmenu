Attribute VB_Name = "Blocks"
Option Explicit
Option Base 0


'Begin Code Block
Public Sub GetBlkRefs(strBlkName As String, objSelSet As AcadSelectionSet)
'  Dim objBlk As AcadBlock
'  Dim colBlks As AcadBlocks
'  Dim objBlkRefs As AcadBlockReference
  Dim varData(0) As Variant
  Dim intData(0) As Integer
  varData(0) = strBlkName
  intData(0) = 2
  objSelSet.Select acSelectionSetAll, , , intData, varData
End Sub

Public Function vbdPowerSet(strName As String) As AcadSelectionSet
  Dim objSelSet As AcadSelectionSet
  Dim objSelCol As AcadSelectionSets
  
  Set objSelCol = ThisDrawing.SelectionSets
  For Each objSelSet In objSelCol
    If objSelSet.Name = strName Then
      ThisDrawing.SelectionSets.Item(strName).Delete
      Exit For
    End If
  Next
  Set objSelSet = ThisDrawing.SelectionSets.Add(strName)
  Set vbdPowerSet = objSelSet
End Function
  
Sub ExcelReNum()
  Dim objExcel As Excel.Application
  Dim i As Integer, j As Integer, val As Integer
  
  Const MAXROW = 1000
  
  'Excel MUST be running for this sample
  Set objExcel = GetObject(, "Excel.Application")

  With objExcel
    i = .Selection.row
    j = .Selection.Column
    val = .Cells(i, j).value
    While i < MAXROW
        i = i + 1
        If .Cells(i, j) <> "" Then
            .Cells(i, j) = val + 1
            val = val + 1
        End If
    Wend
  End With
End Sub

  
Public Sub ImportLeadersFromExcel()
  Dim objSS As AcadSelectionSet
  Dim objblkRef As AcadBlockReference
  Dim objExcel As Excel.Application
  Dim list As New Scripting.Dictionary
  Dim i As Integer, j As Integer, numbers As Boolean, value As String, key As String
  Dim varAtts As Variant, intCnt As Integer, intCnt2 As Integer, found As Boolean
  
  Const MAXROW = 1000
  Const MAXCOL = 256
  
  On Error GoTo Err_Control
  'Excel MUST be running for this sample
  Set objExcel = GetObject(, "Excel.Application")

  With objExcel
    'Ищем строку с надписью Поз. в первой колонке
    For i = 1 To MAXROW
        If .Cells(i, 1) = "Поз." Then
            Exit For
        End If
    Next i
    If i >= MAXROW Then
        MsgBox ("Откройте документ эксель с надписью Поз. в первой колонке")
        Exit Sub
    End If
    
    'в найденной строке ищем ячейку со значением TAG
    For j = 1 To MAXCOL
        If .Cells(i, j) = "TAG" Then
            Exit For
        End If
    Next j
    If j >= MAXCOL Then
        MsgBox ("Не найдена надпись TAG в одной строке с Поз.")
        Exit Sub
    End If
    
    While i < MAXROW
        i = i + 1
        If .Cells(i, j).value <> "" Then
            value = .Cells(i, 1).value
            key = .Cells(i, j).value
            If list.Exists(key) Then
                MsgBox ("В строке " + str(i) + " найден повторяющийся TAG")
                Exit Sub
            End If
            list(key) = value
        End If
    Wend
  End With
  
'  MsgBox (str(list.Count))
  
  Set objSS = vbdPowerSet("mdv3")
  
  GetBlkRefs "mdv,`*U*", objSS
  
'  MsgBox ("Найдено " & str(objSS.Count) & " блоков")
  
  For Each objblkRef In objSS
   If objblkRef.HasAttributes And objblkRef.EffectiveName = "mdv" Then
      varAtts = objblkRef.GetAttributes
      For intCnt = LBound(varAtts) To UBound(varAtts)
        If varAtts(intCnt).TagString = "TAG" Then
            For intCnt2 = LBound(varAtts) To UBound(varAtts)
                If varAtts(intCnt2).TagString = "NUM" Then
                    If list.Exists(varAtts(intCnt).TextString) Then
                        varAtts(intCnt2).TextString = list(varAtts(intCnt).TextString)
                    Else
                        varAtts(intCnt2).TextString = "TAG не найден"
                    End If
                    Exit For
                End If
            Next intCnt2
        End If
      Next
   End If
  Next objblkRef
  
Exit_Here:
  Exit Sub
Err_Control:
  MsgBox err.Description
  Resume Exit_Here
  
End Sub

Attribute VB_Name = "DlgBend"
Attribute VB_Base = "0{DF51657C-A953-4AD3-A2B8-2E649C86D099}{DCF5F1E8-CA4C-4BCB-A20F-19ADB69F8FE8}"
Attribute VB_GlobalNameSpace = False
Attribute VB_Creatable = False
Attribute VB_PredeclaredId = True
Attribute VB_Exposed = False
Attribute VB_TemplateDerived = False
Attribute VB_Customizable = False
Option Explicit

Private Sub accept_Click()
    DlgOK = True
    ListIdx = tr_list.ListIndex
    DrawScale = CDbl(scalebox.text)
    If opt45.value = True Then
        Curve = dtr(45)
    ElseIf opt60.value = True Then
        Curve = dtr(60)
    ElseIf opt90.value = True Then
        Curve = dtr(90)
    Else
        Curve = dtr(180)
    End If
    hide
End Sub

Private Sub cancel_Click()
    hide
End Sub

Private Sub UserForm_Initialize()
 
DrawScale = ThisDrawing.GetVariable("dimlfac")
scalebox.text = format(DrawScale)

End Sub

Attribute VB_Name = "DlgExpLine"
Attribute VB_Base = "0{8BFBC4EA-087C-4463-84F4-113B57A0D4B2}{4603525F-DCA7-4C8D-B290-2009EF5DDB7D}"
Attribute VB_GlobalNameSpace = False
Attribute VB_Creatable = False
Attribute VB_PredeclaredId = True
Attribute VB_Exposed = False
Attribute VB_TemplateDerived = False
Attribute VB_Customizable = False
Option Explicit

Private Sub CommandButton1_Click()
    DlgOK = True
    If TextBox1.value = "" Or TextBox2.value = "" Or TextBox3.value = "" Then
        MsgBox "Введите ченить в поля ввода"
        Exit Sub
    End If
    DlgExpLine.hide
End Sub

Private Sub CommandButton2_Click()
    DlgOK = False
    DlgExpLine.hide

End Sub

Attribute VB_Name = "DlgLeader"
Attribute VB_Base = "0{3A715D45-0221-4462-8807-81E9B78ED93A}{7FEF0E02-D1F5-4EB8-B207-266FC9B7FE92}"
Attribute VB_GlobalNameSpace = False
Attribute VB_Creatable = False
Attribute VB_PredeclaredId = True
Attribute VB_Exposed = False
Attribute VB_TemplateDerived = False
Attribute VB_Customizable = False
Option Explicit

Private Sub CommandButton1_Click()
    DlgOK = True
    ListIdx = l_list.ListIndex
    hide
End Sub

Private Sub CommandButton2_Click()
    hide
End Sub

Attribute VB_Name = "DlgNewPipe"
Attribute VB_Base = "0{9DF4EE61-C01C-4D13-B192-88C2D88B8EC1}{6D796CD6-3C33-4069-974E-BF797BD992BD}"
Attribute VB_GlobalNameSpace = False
Attribute VB_Creatable = False
Attribute VB_PredeclaredId = True
Attribute VB_Exposed = False
Attribute VB_TemplateDerived = False
Attribute VB_Customizable = False
Private Sub ComboBox1_Change()

End Sub

Private Sub CommandButton1_Click()
    DlgOK = True
    DlgNewPipe.hide
End Sub

Private Sub CommandButton2_Click()
    DlgNewPipe.hide
End Sub

Private Sub CommandButton3_Click()
    CheckBox1.value = 1
    CheckBox2.value = 1
    CheckBox3.value = 1
    CheckBox4.value = 1
    CheckBox5.value = 1
    CheckBox6.value = 1
    CheckBox7.value = 1
    CheckBox8.value = 1
    CheckBox9.value = 1
    CheckBox10.value = 1
End Sub

Private Sub CommandButton4_Click()
    CheckBox1.value = 0
    CheckBox2.value = 0
    CheckBox3.value = 0
    CheckBox4.value = 0
    CheckBox5.value = 0
    CheckBox6.value = 0
    CheckBox7.value = 0
    CheckBox8.value = 0
    CheckBox9.value = 0
    CheckBox10.value = 0
End Sub

Attribute VB_Name = "DlgSkv"
Attribute VB_Base = "0{E1601A39-939D-4200-A25A-682B768314EE}{71A46353-F114-4769-8A62-99AEB065B12E}"
Attribute VB_GlobalNameSpace = False
Attribute VB_Creatable = False
Attribute VB_PredeclaredId = True
Attribute VB_Exposed = False
Attribute VB_TemplateDerived = False
Attribute VB_Customizable = False
Private Sub CommandButton1_Click()
DlgOK = True
DlgSkv.hide
End Sub

Private Sub CommandButton2_Click()
TextBox1.value = ""
TextBox2.value = ""
TextBox3.value = ""
TextBox4.value = ""
TextBox5.value = ""
End Sub

Private Sub CommandButton3_Click()
DlgOK = False
DlgSkv.hide
End Sub

Attribute VB_Name = "DlgTees"
Attribute VB_Base = "0{E7413436-A679-47A2-AB3C-C0DE2DB6A07F}{B1A12C1E-D0CB-4C64-8FB4-5AC2957AD523}"
Attribute VB_GlobalNameSpace = False
Attribute VB_Creatable = False
Attribute VB_PredeclaredId = True
Attribute VB_Exposed = False
Attribute VB_TemplateDerived = False
Attribute VB_Customizable = False
Option Explicit

Private Sub accept_Click()
    DlgOK = True
    ListIdx = tr_list.ListIndex
    DrawScale = CDbl(scalebox.text)
    hide
End Sub

Private Sub cancel_Click()
    hide
End Sub

Private Sub UserForm_Initialize()

DrawScale = ThisDrawing.GetVariable("dimlfac")
scalebox.text = format(DrawScale)

End Sub

Attribute VB_Name = "DlgTran"
Attribute VB_Base = "0{E857F1DD-95A4-4479-A20E-97538569EB0A}{14A8B9DB-48B2-4AD7-8CE6-BBA75BBADB25}"
Attribute VB_GlobalNameSpace = False
Attribute VB_Creatable = False
Attribute VB_PredeclaredId = True
Attribute VB_Exposed = False
Attribute VB_TemplateDerived = False
Attribute VB_Customizable = False
Private Sub CommandButton1_Click()
hide
End Sub

Attribute VB_Name = "Draw"
Option Explicit
Option Base 0

Sub draw_dims()
' 13.09.2013 - проставить размеры для всех линий по длине линии
    Dim sset As AcadSelectionSet
    Dim Line As AcadLine
    Dim FilterType(0) As Integer
    Dim FilterData(0) As Variant
    Dim dims As AcadDimAligned
    Dim ActSpace As Variant
    
    Set ActSpace = GetActiveSpace()
    
    Set sset = GetSelSet("mdv")
    FilterType(0) = 0
    FilterData(0) = "LINE"
    sset.SelectOnScreen FilterType, FilterData
    
    For Each Line In sset
        Set dims = ActSpace.AddDimAligned(Line.StartPoint, Line.EndPoint, Line.EndPoint)
    Next Line
    sset.Delete
End Sub

Sub draw_line1()
' 30.09.2013 - нарисовать на верхнем конце линии горизонтальную линию длиной 1мм
    Dim sset As AcadSelectionSet
    Dim Line As AcadLine, l1 As AcadLine
    Dim FilterType(0) As Integer
    Dim FilterData(0) As Variant
    Dim ActSpace As Variant
    Dim sp(0 To 2) As Double, ep(0 To 2) As Double
    
    Set ActSpace = GetActiveSpace()
    
    Set sset = GetSelSet("mdv")
    FilterType(0) = 0
    FilterData(0) = "LINE"
    sset.SelectOnScreen FilterType, FilterData
    
    For Each Line In sset
        If Line.StartPoint(1) > Line.EndPoint(1) Then
            sp(1) = Line.StartPoint(1)
            ep(1) = Line.StartPoint(1)
        Else
            sp(1) = Line.EndPoint(1)
            ep(1) = Line.EndPoint(1)
        End If
        sp(0) = Line.StartPoint(0) - 0.5
        ep(0) = Line.StartPoint(0) + 0.5
        Set l1 = ActSpace.AddLine(sp, ep)
    Next Line
    sset.Delete
End Sub

Sub SetObjLayer(ByRef obj As Acad3DSolid, lay As String)
    Dim layerObj As AcadLayers, l As AcadLayer
    Dim IsFound As Boolean
    IsFound = False
    Set layerObj = ThisDrawing.Layers
    For Each l In layerObj
        If l.Name = lay Then
            IsFound = True
            Exit For
        End If
    Next l
    If Not IsFound Then
        layerObj.Add (lay)
    End If
    obj.Layer = lay
End Sub

Function MakeVector(l As AcadLine) As Double()
Dim v(0 To 2) As Double
    v(0) = l.EndPoint(0) - l.StartPoint(0)
    v(1) = l.EndPoint(1) - l.StartPoint(1)
    v(2) = l.EndPoint(2) - l.StartPoint(2)
    MakeVector = v
End Function

Function MakeVector2(sp() As Double, ep() As Double) As Double()
Dim v(0 To 2) As Double
    v(0) = ep(0) - sp(0)
    v(1) = ep(1) - sp(1)
    v(2) = ep(2) - sp(2)
    MakeVector2 = v
End Function

Function VectorMul(v1() As Double, v2() As Double) As Double()
    Dim v3(0 To 2) As Double
    v3(0) = v1(1) * v2(2) - v1(2) * v2(1)
    v3(1) = v1(0) * v2(2) - v1(2) * v2(0)
    v3(2) = v1(0) * v2(1) - v1(1) * v2(0)
    VectorMul = v3
End Function

Sub LineToPipe()
'Отконвертировать линии в трубу
    Static d As Integer, DX As Double, beta As Double
    Dim sset As AcadSelectionSet, i As Integer, entry As AcadEntity, retCoord As Variant
    Dim Line As AcadLine, ll As AcadLine
    
    ' ActiveViewport
    
'    D = GetTextDefault(str(D), "Диаметр: ")
'    dx = GetTextDefault(str(dx), "Толщина стенки: ")
    d = 100: DX = 10
    Set sset = GetSelSet("mdv")
    Dim FilterType(0) As Integer
    Dim FilterData(0) As Variant
    FilterType(0) = 0
    FilterData(0) = "LINE"
    sset.SelectOnScreen FilterType, FilterData
    
    For Each Line In sset
        Dim newUCS As AcadUCS
        Dim currUcs As AcadUCS
        Dim origin(0 To 2) As Double
        Dim xAxis(0 To 2) As Double
        Dim yAxis(0 To 2) As Double
        Dim cc As Variant
        
        ' Get the current saved UCS of the active document. If the current UCS is
        ' not saved, then add a new UCS to the UserCoordinateSystems collection
'        If ThisDrawing.GetVariable("UCSNAME") = "" Then
'            ' Current UCS is not saved so get the data and save it
'            With ThisDrawing
'                Set currUCS = .UserCoordinateSystems.Add( _
'                                .GetVariable("UCSORG"), _
'                                .Utility.TranslateCoordinates(.GetVariable("UCSXDIR"), acUCS, acWorld, 0), _
'                                .Utility.TranslateCoordinates(.GetVariable("UCSYDIR"), acUCS, acWorld, 0), _
'                                "OriginalUCS")
'            End With
'        Else
'            Set currUCS = ThisDrawing.ActiveUCS  'current UCS is saved
'        End If
        
        ' Create a UCS and make it current
        
        
        origin(0) = Line.StartPoint(0): origin(1) = Line.StartPoint(1): origin(2) = Line.StartPoint(2)
        cc = MakeVector(Line)
        xAxis(0) = Cos(ArcCos(cc(0) / Line.Length) + pi / 2) + Line.StartPoint(0)
        xAxis(1) = Cos(ArcCos(cc(1) / Line.Length) + pi / 2) + Line.StartPoint(1)
        xAxis(2) = Line.StartPoint(2)
        
        Set ll = ThisDrawing.ModelSpace.AddLine(Line.StartPoint, xAxis)
        
        cc = VectorMul(MakeVector(Line), MakeVector2(origin, xAxis))
        yAxis(0) = cc(0)
        yAxis(1) = cc(1)
        yAxis(2) = cc(2)
        Set newUCS = ThisDrawing.UserCoordinateSystems.Add(Line.StartPoint, yAxis, xAxis, "TestUCS")
        ThisDrawing.ActiveUCS = newUCS
       
        Dim regionObj As Variant
        Dim solidObj As Acad3DSolid, solidObj2 As Acad3DSolid
        Dim curves(0 To 0) As AcadEntity
        
        Set curves(0) = ThisDrawing.ModelSpace.AddCircle(Line.StartPoint, d / 2)
        regionObj = ThisDrawing.ModelSpace.AddRegion(curves)
        curves(0).Delete
        Set solidObj = ThisDrawing.ModelSpace.AddExtrudedSolid(regionObj(0), Line.Length, 0)
        regionObj(0).Delete
        
        Set curves(0) = ThisDrawing.ModelSpace.AddCircle(Line.StartPoint, d / 2 - DX)
        regionObj = ThisDrawing.ModelSpace.AddRegion(curves)
        curves(0).Delete
        Set solidObj2 = ThisDrawing.ModelSpace.AddExtrudedSolid(regionObj(0), Line.Length, 0)
        regionObj(0).Delete
        
        solidObj.Boolean acSubtraction, solidObj2
        
        ' Reset the UCS to its previous setting
'        ThisDrawing.ActiveUCS = currUCS
    Next Line
    sset.Delete
End Sub


Sub Draw3Pipe()
' отрисовать 3х мерную трубу
Static d As Double, DX As Double, l As Double
Dim solidObj As Acad3DSolid, pt(0 To 2) As Double
    
    d = GetTextDefault(str(d), "Диаметр: ")
    DX = GetTextDefault(str(DX), "Толщина стенки: ")
    l = GetTextDefault(str(l), "Длина трубы: ")
    MDVGetPoint pt, "Начальная точка: "
    Set solidObj = DrawCilinder(pt, d, l)
    solidObj.Boolean acSubtraction, DrawCilinder(pt, d - 2 * DX, l)
    SetObjLayer solidObj, "lin_Pipe"
End Sub

Function DrawCilinder(pt() As Double, d As Double, l As Double) As Acad3DSolid
Dim curves(0 To 0) As AcadEntity, regionObj As Variant, ms As AcadModelSpace
    Set ms = ThisDrawing.ModelSpace
    Set curves(0) = ms.AddCircle(pt, d / 2)
    regionObj = ms.AddRegion(curves)
    curves(0).Delete
    Set DrawCilinder = ms.AddExtrudedSolid(regionObj(0), l, 0)
    regionObj(0).Delete
End Function

Sub Draw3Kran()
' отрисовать 3Д кран
Static D3 As Double, d As Double, b As Double, l As Double, l1 As Double, H2 As Double, H3 As Double
Const DX = 5 'толщина стенки
Const Lpr = 0.1 'длина 1 и 3 прямого участка от(L)
Const Lpr2 = 0.3 'длина 2 прямого участка от(L)
Const Dpr = 0.25 'отношение диаметра привода к диаметру крана
Const Dpr2 = 0.8 'отношение диаметра цилиндра к диаметру привода
Dim pt(0 To 2) As Double, cp(0 To 2) As Double, cp2(0 To 2) As Double, cp3(0 To 2) As Double, cp4(0 To 2) As Double
Dim curves(0 To 7) As AcadEntity, c As Variant
Dim regionObj As Variant
Dim solidObj As Acad3DSolid, solidObj2 As Acad3DSolid
    D3 = GetTextDefault(str(d), "Диаметр (D3): ")
    d = GetTextDefault(str(d), "Диаметр (D4): ")
    b = GetTextDefault(str(b), "Ширина (B): ")
    l = GetTextDefault(str(l), "Длина (L): ")
    l1 = GetTextDefault(str(l1), "Параметр (L1): ")
    H2 = GetTextDefault(str(H2), "Параметр (H2): ")
    H3 = GetTextDefault(str(H3), "Параметр (H3): ")
    MDVGetPoint pt, "Начальная точка: "
    
    cp(0) = pt(0) + l: cp(1) = pt(1): cp(2) = pt(2)
    Set curves(0) = ThisDrawing.ModelSpace.AddLine(pt, cp)
    
    cp2(0) = cp(0): cp2(1) = cp(1) - d / 2: cp2(2) = cp(2)
    Set curves(1) = ThisDrawing.ModelSpace.AddLine(cp, cp2)

    cp(0) = cp2(0) - l * Lpr: cp(1) = cp2(1): cp(2) = cp2(2)
    Set curves(2) = ThisDrawing.ModelSpace.AddLine(cp2, cp)

    cp2(0) = cp(0) - (l / 2 - (l * Lpr2) / 2 - (l * Lpr)): cp2(1) = cp(1) - (b - d) / 2: cp2(2) = cp(2)
    Set curves(3) = ThisDrawing.ModelSpace.AddLine(cp, cp2)
    
    cp(0) = cp2(0) - l * Lpr2: cp(1) = cp2(1): cp(2) = cp2(2)
    Set curves(4) = ThisDrawing.ModelSpace.AddLine(cp2, cp)
    
    cp2(0) = cp(0) - (l / 2 - (l * Lpr2) / 2 - (l * Lpr)): cp2(1) = cp(1) + (b - d) / 2: cp2(2) = cp(2)
    Set curves(5) = ThisDrawing.ModelSpace.AddLine(cp, cp2)

    cp(0) = cp2(0) - l * Lpr: cp(1) = cp2(1): cp(2) = cp2(2)
    Set curves(6) = ThisDrawing.ModelSpace.AddLine(cp2, cp)

    Set curves(7) = ThisDrawing.ModelSpace.AddLine(cp, pt)
    
    regionObj = ThisDrawing.ModelSpace.AddRegion(curves)
    
    For Each c In curves
        c.Delete
    Next c
    
    cp2(0) = 1: cp2(1) = 0: cp(2) = 0
    Set solidObj = ThisDrawing.ModelSpace.AddRevolvedSolid(regionObj(0), pt, cp2, pi * 2)
    regionObj(0).Delete

    cp2(0) = pt(0) + l / 2: cp2(1) = pt(1): cp2(2) = pt(2) + H3 / 2
    Set solidObj2 = ThisDrawing.ModelSpace.AddCylinder(cp2, d * Dpr, H3)
    solidObj.Boolean acUnion, solidObj2

    cp(0) = cp2(0): cp(1) = cp2(1): cp(2) = cp2(2) + H3 / 2
    Set solidObj2 = ThisDrawing.ModelSpace.AddCylinder(cp, d * Dpr * Dpr2, l1)
    cp2(1) = cp(1) + 1: cp2(2) = cp(2)
    solidObj2.Rotate3D cp2, cp, pi / 2
    solidObj.Boolean acUnion, solidObj2

    If H2 > 0 Then
        'лапка 1
            cp2(0) = pt(0) + l / 2 + l * Lpr2 / 2: cp2(1) = pt(1) + l * Lpr2 / 2: cp2(2) = pt(2) - H2 / 2
            Set solidObj2 = ThisDrawing.ModelSpace.AddBox(cp2, l * Lpr / 2, l * Lpr / 2, H2)
            solidObj.Boolean acUnion, solidObj2
            
        'лапка 2
            cp2(0) = pt(0) + l / 2 + l * Lpr2 / 2: cp2(1) = pt(1) - l * Lpr2 / 2: cp2(2) = pt(2) - H2 / 2
            Set solidObj2 = ThisDrawing.ModelSpace.AddBox(cp2, l * Lpr / 2, l * Lpr / 2, H2)
            solidObj.Boolean acUnion, solidObj2
        
        'лапка 4
            cp2(0) = pt(0) + l / 2 - l * Lpr2 / 2: cp2(1) = pt(1) + l * Lpr2 / 2: cp2(2) = pt(2) - H2 / 2
            Set solidObj2 = ThisDrawing.ModelSpace.AddBox(cp2, l * Lpr / 2, l * Lpr / 2, H2)
            solidObj.Boolean acUnion, solidObj2
            
        'лапка 3
            cp2(0) = pt(0) + l / 2 - l * Lpr2 / 2: cp2(1) = pt(1) - l * Lpr2 / 2: cp2(2) = pt(2) - H2 / 2
            Set solidObj2 = ThisDrawing.ModelSpace.AddBox(cp2, l * Lpr / 2, l * Lpr / 2, H2)
            solidObj.Boolean acUnion, solidObj2
        
        'основание
            CopyPtPlus pt, cp, l / 2, 0, -H2 + l * Lpr2 / 32
            Set solidObj2 = ThisDrawing.ModelSpace.AddBox(cp, l * Lpr2 + l * Lpr, l * Lpr2 + l * Lpr, l * Lpr2 / 16)
            solidObj.Boolean acUnion, solidObj2
    End If

'полость
    Dim cur2(0 To 0) As AcadEntity
    Set cur2(0) = ThisDrawing.ModelSpace.AddCircle(pt, D3 / 2)
    CopyPtPlus pt, cp, 0, 1, 0
    cur2(0).Rotate3D pt, cp, pi / 2
    regionObj = ThisDrawing.ModelSpace.AddRegion(cur2)
    cur2(0).Delete
    Set solidObj2 = ThisDrawing.ModelSpace.AddExtrudedSolid(regionObj(0), l, 0)
    regionObj(0).Delete
    
    solidObj.Boolean acSubtraction, solidObj2
    SetObjLayer solidObj, "lin_Kran"
End Sub

Sub Draw3Zagl()
' отрисовать 3х мерную заглушку
Static d As Integer, DX As Double, l As Integer
Dim pt(0 To 2) As Double, cp(0 To 2) As Double, cp2(0 To 2) As Double, k As Double
Dim curves(0 To 3) As AcadEntity, c As Variant, ug As Double
    d = GetTextDefault(str(d), "Диаметр: ")
    DX = GetTextDefault(str(DX), "Толщина стенки: ")
    l = GetTextDefault(str(l), "Высота: ")
    MDVGetPoint pt, "Начальная точка: "

    Dim regionObj As Variant
    Dim solidObj As Acad3DSolid
    
    k = (d ^ 2 / (8 * l) - l / 2)
    cp(0) = pt(0) - k: cp(1) = pt(1): cp(2) = pt(2)
    ug = Atn(d / (2 * k))
    Set curves(0) = ThisDrawing.ModelSpace.AddArc(cp, k + l, 0, ug)
    
    k = ((d - 2 * DX) ^ 2 / (8 * (l - DX)) - (l - DX) / 2)
    cp(0) = pt(0) - k: cp(1) = pt(1): cp(2) = pt(2)
    ug = Atn((d - 2 * DX) / (2 * k))
    Set curves(1) = ThisDrawing.ModelSpace.AddArc(cp, k + l - DX, 0, ug)
    
    cp(0) = pt(0): cp(1) = pt(1) + d / 2: cp(2) = pt(2)
    cp2(0) = pt(0): cp2(1) = pt(1) + d / 2 - DX: cp2(2) = pt(2)
    Set curves(2) = ThisDrawing.ModelSpace.AddLine(cp, cp2)
    
    cp(0) = pt(0) + l: cp(1) = pt(1): cp(2) = pt(2)
    cp2(0) = pt(0) + l - DX: cp2(1) = pt(1): cp2(2) = pt(2)
    Set curves(3) = ThisDrawing.ModelSpace.AddLine(cp, cp2)
    
    regionObj = ThisDrawing.ModelSpace.AddRegion(curves)
    
    For Each c In curves
        c.Delete
    Next c
    
    cp2(0) = 1: cp2(1) = 0: cp(2) = 0
    Set solidObj = ThisDrawing.ModelSpace.AddRevolvedSolid(regionObj(0), cp, cp2, pi * 2)
    regionObj(0).Delete
    SetObjLayer solidObj, "lin_Zagl"
End Sub

Sub Draw3Pereh()
' отрисовать 3х мерный переход
Static d As Double, d1 As Double, DX As Double, l As Integer, Ugol As Double, DX1 As Double
Dim pt(0 To 2) As Double, cp(0 To 2) As Double
Dim curves(0 To 0) As AcadEntity
    d = GetTextDefault(str(d), "Диаметр основания: ")
    DX = GetTextDefault(str(DX), "Толщина стенки основания: ")
    d1 = GetTextDefault(str(d), "Диаметр вершины: ")
    DX1 = GetTextDefault(str(DX1), "Толщина стенки вершины: ")
    l = GetTextDefault(str(l), "Длина перехода: ")
    MDVGetPoint pt, "Начальная точка: "

    Dim regionObj As Variant
    Dim solidObj As Acad3DSolid, solidObj2 As Acad3DSolid
    
    Ugol = Atn(((d - d1) / 2) / l)
    
    Set curves(0) = ThisDrawing.ModelSpace.AddCircle(pt, d / 2)
    regionObj = ThisDrawing.ModelSpace.AddRegion(curves)
    curves(0).Delete
    Set solidObj = ThisDrawing.ModelSpace.AddExtrudedSolid(regionObj(0), l, Ugol)
    regionObj(0).Delete
    
    Ugol = Atn((((d - DX * 2) - (d1 - DX1 * 2)) / 2) / l)
    
    Set curves(0) = ThisDrawing.ModelSpace.AddCircle(pt, d / 2 - DX)
    regionObj = ThisDrawing.ModelSpace.AddRegion(curves)
    curves(0).Delete
    Set solidObj2 = ThisDrawing.ModelSpace.AddExtrudedSolid(regionObj(0), l, Ugol)
    regionObj(0).Delete
    
    solidObj.Boolean acSubtraction, solidObj2
    
    cp(0) = pt(0): cp(1) = pt(1) + 5: cp(2) = pt(2)
    solidObj.Rotate3D pt, cp, pi / 2
    SetObjLayer solidObj, "lin_Perehod"
End Sub

Sub Draw3Troy()
'тройник 3Д
Static d As Double, DX As Double, l As Double
Static d1 As Double, DX1 As Double, l1 As Double
Dim pt(0 To 2) As Double, cp(0 To 2) As Double, cp2(0 To 2) As Double
Dim curves(0 To 0) As AcadEntity
    d = GetTextDefault(str(d), "Диаметр основания: ")
    DX = GetTextDefault(str(DX), "Толщина стенки основания: ")
    l = GetTextDefault(str(l), "Длина тройника: ")
    d1 = GetTextDefault(str(d1), "Диаметр отвода: ")
    DX1 = GetTextDefault(str(DX1), "Толщина стенки отвода: ")
    l1 = GetTextDefault(str(l1), "Высота тройника: ")
    MDVGetPoint pt, "Начальная точка: "

    Dim regionObj As Variant
    Dim solidObj As Acad3DSolid, solidObj2 As Acad3DSolid
    
    Set curves(0) = ThisDrawing.ModelSpace.AddCircle(pt, d / 2)
    regionObj = ThisDrawing.ModelSpace.AddRegion(curves)
    curves(0).Delete
    Set solidObj = ThisDrawing.ModelSpace.AddExtrudedSolid(regionObj(0), l, 0)
    regionObj(0).Delete

    cp(0) = pt(0): cp(1) = pt(1): cp(2) = pt(2) + l / 2
    cp2(0) = cp(0): cp2(1) = cp(1) + 1: cp2(2) = cp(2)
    
    Set curves(0) = ThisDrawing.ModelSpace.AddCircle(cp, d1 / 2)
    curves(0).Rotate3D cp, cp2, pi * 90 / 180
    regionObj = ThisDrawing.ModelSpace.AddRegion(curves)
    curves(0).Delete
    Set solidObj2 = ThisDrawing.ModelSpace.AddExtrudedSolid(regionObj(0), l1, 0)
    regionObj(0).Delete

    solidObj.Boolean acUnion, solidObj2

    Set curves(0) = ThisDrawing.ModelSpace.AddCircle(pt, d / 2 - DX)
    regionObj = ThisDrawing.ModelSpace.AddRegion(curves)
    curves(0).Delete
    Set solidObj2 = ThisDrawing.ModelSpace.AddExtrudedSolid(regionObj(0), l, 0)
    regionObj(0).Delete

    solidObj.Boolean acSubtraction, solidObj2

    Set curves(0) = ThisDrawing.ModelSpace.AddCircle(cp, d1 / 2 - DX1)
    curves(0).Rotate3D cp, cp2, pi * 90 / 180
    regionObj = ThisDrawing.ModelSpace.AddRegion(curves)
    curves(0).Delete
    Set solidObj2 = ThisDrawing.ModelSpace.AddExtrudedSolid(regionObj(0), l1, 0)
    regionObj(0).Delete

    solidObj.Boolean acSubtraction, solidObj2
    
    cp(0) = pt(0): cp(1) = pt(1) + 5: cp(2) = pt(2)
    solidObj.Rotate3D pt, cp, pi / 2
    cp(0) = pt(0) + 5: cp(1) = pt(1): cp(2) = pt(2)
    solidObj.Rotate3D pt, cp, pi
    SetObjLayer solidObj, "lin_Troy"

End Sub

Sub Draw3Otvod()
' отрисовать 3Д отвод 90
Static d As Integer, DX As Double, R As Double
Dim pt(0 To 2) As Double, cp(0 To 2) As Double, Arc As AcadArc
Dim curves(0 To 0) As AcadEntity
    d = GetTextDefault(str(d), "Диаметр: ")
    DX = GetTextDefault(str(DX), "Толщина стенки: ")
    R = GetTextDefault(str(R), "Радиус отвода: ")
    MDVGetPoint pt, "Начальная точка: "
    
    cp(0) = pt(0) - R: cp(1) = pt(1): cp(2) = pt(2)
    Set Arc = ThisDrawing.ModelSpace.AddArc(cp, R, 0, 90 * 3.14159265358979 / 180)
    Arc.Rotate3D cp, pt, 90 * 3.14159265358979 / 180
    
    Dim regionObj As Variant
    Dim solidObj As Acad3DSolid, solidObj2 As Acad3DSolid
    
    Set curves(0) = ThisDrawing.ModelSpace.AddCircle(pt, d / 2)
    regionObj = ThisDrawing.ModelSpace.AddRegion(curves)
    curves(0).Delete
    Set solidObj = ThisDrawing.ModelSpace.AddExtrudedSolidAlongPath(regionObj(0), Arc)
    regionObj(0).Delete
    
    Set curves(0) = ThisDrawing.ModelSpace.AddCircle(pt, d / 2 - DX)
    regionObj = ThisDrawing.ModelSpace.AddRegion(curves)
    curves(0).Delete
    Set solidObj2 = ThisDrawing.ModelSpace.AddExtrudedSolidAlongPath(regionObj(0), Arc)
    regionObj(0).Delete
    
    solidObj.Boolean acSubtraction, solidObj2
    Arc.Delete
    
    cp(0) = pt(0): cp(1) = pt(1) + 5: cp(2) = pt(2)
    solidObj.Rotate3D pt, cp, pi / 2
    SetObjLayer solidObj, "lin_Otvod"
End Sub

' Загрузить список всех выносок в диалог и отрисовать выбранную
Sub TextLead()
    Dim FileNumber As Integer, i As Long, FileName As String, Lead() As String

    FileName = MDVPath + "leaders.txt"
    FileNumber = FreeFile
    Open FileName For Input Access Read As #FileNumber
    i = 0
    Load DlgLeader
    DlgLeader.l_list.Clear
    Do While Not EOF(FileNumber)
        ReDim Preserve Lead(i)
        Line Input #FileNumber, Lead(i)
        DlgLeader.l_list.AddItem Lead(i)
        i = i + 1
    Loop
    Close #FileNumber
    DlgLeader.l_list.ListIndex = 0
    DlgOK = False
    DlgLeader.Show
    If DlgOK Then
        DrawTextLead Lead(ListIdx)
    End If
End Sub

' нарисовать мультивыноску с заданным текстом
Sub DrawTextLead(text As String)
    Dim l As AcadMLeader
    Dim ActSpace As Variant
    Dim sp(0 To 2) As Double, ep(0 To 2) As Double
    Dim points(0 To 5) As Double
    Dim i As Long
    
    If ThisDrawing.ActiveSpace = acModelSpace Then
        Set ActSpace = ThisDrawing.ModelSpace
    Else
        If ThisDrawing.MSpace = True Then
            Set ActSpace = ThisDrawing.ModelSpace
        Else
            Set ActSpace = ThisDrawing.PaperSpace
        End If
    End If

' точка указывающая на подписываемый объект
    MDVGetPoint sp, "Что подписываем: "
' точка начала или конца выноски
    MDVGetPointDir ep, sp, "Где подписываем: "
    
    ' Define the leader points
    points(0) = sp(0): points(1) = sp(1): points(2) = sp(2)
    points(3) = ep(0): points(4) = ep(1): points(5) = ep(2)
    
    Set l = ActSpace.AddMLeader(points, i)
    l.TextString = text
End Sub

Function GetTextDefault(defstring As String, prompt As String) As String
    Dim returnString As String
    returnString = ThisDrawing.Utility.GetString(True, prompt + " <" + defstring + ">:")
    If returnString = "" Then
        GetTextDefault = defstring
    Else
        GetTextDefault = returnString
    End If
End Function

Sub DrawPolka()
    Dim sp(0 To 2) As Double, ep(0 To 2) As Double, p1(0 To 2) As Double, p2(0 To 2) As Double
    Dim a As Double
    Const TextHeight = 2.5, H = 30, dh = 4, l = 2 * 2 ^ 0.5 / 2
    MDVGetPoint sp, "Начальная точка: "
    MDVGetPointDir ep, sp, "Конечная точка: "
    a = ThisDrawing.Utility.AngleFromXAxis(ep, sp)
    Dim lineObj As AcadLine
' левая сторона
    CopyPt sp, p1
    p1(1) = p1(1) + H
    Set lineObj = ThisDrawing.ModelSpace.AddLine(sp, p1)
' правая сторона
    CopyPt ep, p2
    p2(1) = p2(1) + H
    Set lineObj = ThisDrawing.ModelSpace.AddLine(ep, p2)
' перемычка
    p1(0) = sp(0) - dh: p1(1) = sp(1) + H - dh
    p2(0) = ep(0) + dh: p2(1) = ep(1) + H - dh
    Set lineObj = ThisDrawing.ModelSpace.AddLine(p1, p2)
' левая засечка
    p1(0) = sp(0) - l: p1(1) = sp(1) + H - dh - l
    p2(0) = sp(0) + l: p2(1) = sp(1) + H - dh + l
    Set lineObj = ThisDrawing.ModelSpace.AddLine(p1, p2)
' правая засечка
    p1(0) = ep(0) - l: p1(1) = ep(1) + H - dh - l
    p2(0) = ep(0) + l: p2(1) = ep(1) + H - dh + l
    Set lineObj = ThisDrawing.ModelSpace.AddLine(p1, p2)
    Dim txt As AcadText
    p1(0) = sp(0) - 0.5: p1(1) = sp(1)
    Set txt = ThisDrawing.ModelSpace.AddText("ПК", p1, TextHeight)
    txt.Rotate p1, dtr(90)
    p1(0) = ep(0) + TextHeight + 0.5: p1(1) = ep(1)
    Set txt = ThisDrawing.ModelSpace.AddText("ПК", p1, TextHeight)
    txt.Rotate p1, dtr(90)
    p1(0) = (sp(0) + ep(0)) / 2: p1(1) = sp(1) + H - dh + 0.5
    Set txt = ThisDrawing.ModelSpace.AddText("text", p1, TextHeight)
    txt.Alignment = acAlignmentBottomCenter
    txt.TextAlignmentPoint = p1
End Sub

Sub DrawLand()
' Рисовать засечки уровня земли
    Dim sp(0 To 2) As Double, ep(0 To 2) As Double
    Dim a As Double, dlina As Double, i As Double
    Dim pp1 As Variant, zc As Integer
    Dim lineObj As AcadLine
    Const INT1 = 2    'интервал между ближними засечками
    Const INT2 = 15    'интервал между дальними засечками
    Const l = 2.7 'длина засечки
    MDVGetPoint sp, "Начальная точка: "
    MDVGetPointDir ep, sp, "Конечная точка: "
    a = ThisDrawing.Utility.AngleFromXAxis(ep, sp)
    dlina = distance(sp, ep)
    i = 0
    zc = 0
    While i < Abs(dlina)
        ep(0) = sp(0) - i * Cos(a)
        ep(1) = sp(1) - i * Sin(a)
        pp1 = ThisDrawing.Utility.PolarPoint(ep, a + Rad(45), l)
        Set lineObj = ThisDrawing.ModelSpace.AddLine(ep, pp1)
        zc = zc + 1
        If ((zc Mod 3) = 0) Then
            i = i + INT2
        Else
            i = i + INT1
        End If
    Wend
End Sub

Sub DrawValic()
    Dim sp(0 To 2) As Double, ep(0 To 2) As Double, p1(0 To 2) As Double, p2(0 To 2) As Double
    Dim a As Double, dlina As Double, i As Double
    Dim pp1 As Variant, pp2 As Variant
    Dim k1, k2, k3, k4, k5, k6, k7, k8
    Dim first As Boolean
    Const l1 = 2.5, L2 = 5, dL = 2
    MDVGetPoint sp, "Начальная точка: "
    MDVGetPointDir ep, sp, "Конечная точка: "
    a = ThisDrawing.Utility.AngleFromXAxis(ep, sp)
    Dim lineObj As AcadLine
    dlina = distance(sp, ep)
'    MsgBox dlina
    i = 0
    first = True
    While i < Abs(dlina)
        'маленькая засечка
        ep(0) = sp(0) - i * Cos(a)
        ep(1) = sp(1) - i * Sin(a)
        pp1 = ThisDrawing.Utility.PolarPoint(ep, a - Rad(90), l1 / 2)
        pp2 = ThisDrawing.Utility.PolarPoint(ep, a + Rad(90), l1 / 2)
        Set lineObj = ThisDrawing.ModelSpace.AddLine(pp1, pp2)
        If first Then
            k1 = pp1: k8 = pp2
        End If
        i = i + dL
        'большая засечка
        ep(0) = sp(0) - i * Cos(a)
        ep(1) = sp(1) - i * Sin(a)
        pp1 = ThisDrawing.Utility.PolarPoint(ep, a - Rad(90), L2 / 2)
        pp2 = ThisDrawing.Utility.PolarPoint(ep, a + Rad(90), L2 / 2)
        Set lineObj = ThisDrawing.ModelSpace.AddLine(pp1, pp2)
        If first Then
            k2 = pp1: k7 = pp2: first = False
        End If
        i = i + dL
        k3 = pp1: k6 = pp2
    Wend
    'последняя маленькая засечка
    ep(0) = sp(0) - i * Cos(a)
    ep(1) = sp(1) - i * Sin(a)
    k4 = ThisDrawing.Utility.PolarPoint(ep, a - Rad(90), l1 / 2)
    k5 = ThisDrawing.Utility.PolarPoint(ep, a + Rad(90), l1 / 2)
    
    'рамка вокруг засечек
    Set lineObj = ThisDrawing.ModelSpace.AddLine(k1, k2)
    Set lineObj = ThisDrawing.ModelSpace.AddLine(k2, k3)
    Set lineObj = ThisDrawing.ModelSpace.AddLine(k3, k4)
    Set lineObj = ThisDrawing.ModelSpace.AddLine(k4, k5)
    Set lineObj = ThisDrawing.ModelSpace.AddLine(k5, k6)
    Set lineObj = ThisDrawing.ModelSpace.AddLine(k6, k7)
    Set lineObj = ThisDrawing.ModelSpace.AddLine(k7, k8)
End Sub

Function distance(p1() As Double, p2() As Double) As Double
    distance = ((p1(0) - p2(0)) ^ 2 + (p1(1) - p2(1)) ^ 2) ^ 0.5
End Function

Attribute VB_Name = "Furnitura"
Option Explicit
Option Base 0

Public Const ArrSize = 100

'тройники по гост 17376-2001 исп2
Type TeesRecord
    DN As Integer
    d As Integer
    d1 As Integer
    f As Integer
    H As Integer
End Type

'отводы по ГОСТ 17375-2001 исп2
Type BendRecord
    DN As Integer
    d As Integer
    R As Integer
End Type

'переходы по ГОСТ 17378-2001 исп.2
Type ReducerRecord
    DN As Integer
    d As Integer
    d1 As Integer
    l As Integer
End Type

'заглушки по ГОСТ 17379-2001 исп.2
Type CapRecord
    DN As Integer
    d As Integer
    k As Integer
End Type

Public TeesAr(ArrSize) As TeesRecord
Public BendAr(ArrSize) As BendRecord
Public ReducerAr(ArrSize) As ReducerRecord
Public CapAr(ArrSize) As CapRecord
Public DlgOK As Boolean
Public DrawScale As Double
Public Curve As Double
Public ListIdx As Variant

Sub Tees()
    Dim FileNumber As Integer, i As Long, FileName As String

    FileName = MDVPath + "gost_tees"
    FileNumber = FreeFile
    Open FileName For Input Access Read As #FileNumber
    i = 0
    Load DlgTees
    DlgTees.tr_list.Clear
    Do While Not EOF(FileNumber)
        Input #FileNumber, TeesAr(i).DN, TeesAr(i).d, TeesAr(i).d1, TeesAr(i).f, TeesAr(i).H
        DlgTees.tr_list.AddItem ("Ду" + format(TeesAr(i).DN) + " " + format(TeesAr(i).d) + _
            "x" + format(TeesAr(i).d1) + " (F=" + format(TeesAr(i).f) + ", H=" + _
            format(TeesAr(i).H) + ")")
        i = i + 1
    Loop
    Close #FileNumber
    DlgTees.tr_list.ListIndex = 0
    DlgTees.Caption = "Тройники по ГОСТ 17376-2001"
    DlgTees.scalebox.text = format(ThisDrawing.GetVariable("dimlfac"))
    DlgOK = False
    DlgTees.Show
    If DlgOK Then
        Dim varRet As Variant, sp(0 To 2) As Double, angle As Double
        varRet = ThisDrawing.Utility.GetPoint(, "Точка вставки (пересечение осей главной труби и отвода): ")
        sp(0) = varRet(0)
        sp(1) = varRet(1)
        sp(2) = varRet(2)
        angle = ThisDrawing.Utility.GetAngle(varRet, "Направление отвода:")
        DrawTees sp, angle, TeesAr(ListIdx), DrawScale
    End If
End Sub

Sub Bend()
    Dim FileNumber As Integer, i As Long, FileName As String

    Load DlgBend
    DlgTees.tr_list.Clear
    FileName = MDVPath + "gost_bend"
    FileNumber = FreeFile
    Open FileName For Input Access Read As #FileNumber
    i = 0
    DlgBend.tr_list.Clear
    Do While Not EOF(FileNumber) ' Цикл до конца файла.
        Input #FileNumber, BendAr(i).DN, BendAr(i).d, BendAr(i).R
        DlgBend.tr_list.AddItem ("Ду" + format(BendAr(i).DN) + " " + format(BendAr(i).d) + _
            " (R=" + format(BendAr(i).R) + ")")
        i = i + 1
    Loop
    Close #FileNumber
    DlgBend.tr_list.ListIndex = 0
    DlgBend.scalebox.text = format(ThisDrawing.GetVariable("dimlfac"))
    DlgOK = False
    DlgBend.Show
    If DlgOK Then
        Dim varRet As Variant, p1(0 To 2) As Double, p2(0 To 2) As Double, p3(0 To 2) As Double, _
            angle1 As Double, angle2 As Double
        varRet = ThisDrawing.Utility.GetPoint(, "Начальная точка: ")
        p1(0) = varRet(0)
        p1(1) = varRet(1)
        p1(2) = varRet(2)
        varRet = ThisDrawing.Utility.GetPoint(varRet, "Направление 1: ")
        p2(0) = varRet(0)
        p2(1) = varRet(1)
        p2(2) = varRet(2)
        angle1 = ThisDrawing.Utility.AngleFromXAxis(p1, p2)
        angle2 = ThisDrawing.Utility.GetAngle(varRet, "Направление 2:")
        DrawBend p1, angle1, angle2, BendAr(ListIdx), DrawScale, Curve
    End If
End Sub

Sub Reducer()
    Dim FileNumber As Integer, i As Long, FileName As String

    FileName = MDVPath + "gost_reducer"
    FileNumber = FreeFile
    Open FileName For Input Access Read As #FileNumber
    i = 0
    Load DlgTees
    DlgTees.tr_list.Clear
    Do While Not EOF(FileNumber)
        Input #FileNumber, ReducerAr(i).DN, ReducerAr(i).d, ReducerAr(i).d1, ReducerAr(i).l
        DlgTees.tr_list.AddItem ("Ду" + format(ReducerAr(i).DN) + " " + format(ReducerAr(i).d) + _
            "x" + format(ReducerAr(i).d1) + " (L=" + format(ReducerAr(i).l) + ")")
        i = i + 1
    Loop
    Close #FileNumber
    DlgTees.tr_list.ListIndex = 0
    DlgTees.Caption = "Переходы по ГОСТ 17378-2001"
    DlgTees.scalebox.text = format(ThisDrawing.GetVariable("dimlfac"))
    DlgOK = False
    DlgTees.Show
    If DlgOK Then
        Dim varRet As Variant, sp(0 To 2) As Double, angle As Double
        varRet = ThisDrawing.Utility.GetPoint(, "Точка вставки (середина большего основания): ")
        sp(0) = varRet(0)
        sp(1) = varRet(1)
        sp(2) = varRet(2)
        angle = ThisDrawing.Utility.GetAngle(varRet, "Направление:")
        DrawReducer sp, angle, ReducerAr(ListIdx), DrawScale
    End If
End Sub

Sub Cap()
    Dim FileNumber As Integer, i As Long, FileName As String

    FileName = MDVPath + "gost_cap"
    FileNumber = FreeFile
    Open FileName For Input Access Read As #FileNumber
    i = 0
    Load DlgTees
    DlgTees.tr_list.Clear
    Do While Not EOF(FileNumber)
        Input #FileNumber, CapAr(i).DN, CapAr(i).d, CapAr(i).k
        DlgTees.tr_list.AddItem ("Ду" + format(CapAr(i).DN) + " " + format(CapAr(i).d) + _
            " (K=" + format(CapAr(i).k) + ")")
        i = i + 1
    Loop
    Close #FileNumber
    DlgTees.tr_list.ListIndex = 0
    DlgTees.Caption = "Заглушки по ГОСТ 17379-2001"
    DlgTees.scalebox.text = format(ThisDrawing.GetVariable("dimlfac"))
    DlgOK = False
    DlgTees.Show
    If DlgOK Then
        Dim varRet As Variant, sp(0 To 2) As Double, angle As Double
        varRet = ThisDrawing.Utility.GetPoint(, "Точка вставки (середина основания): ")
        sp(0) = varRet(0)
        sp(1) = varRet(1)
        sp(2) = varRet(2)
        angle = ThisDrawing.Utility.GetAngle(varRet, "Направление:")
        DrawCapBlock sp, angle, CapAr(ListIdx), DrawScale
    End If
End Sub

Sub DrawTees(pt() As Double, angle As Double, tr As TeesRecord, tr_m As Double)
    Dim varRet As Variant, DirTop As Double, DirBottom As Double, DirLeft As Double, DirRigth As Double
    Dim points(0 To 19) As Double
    Dim pline As AcadLWPolyline
    Dim ActSpace As Variant

    If ThisDrawing.ActiveSpace = acModelSpace Then
        Set ActSpace = ThisDrawing.ModelSpace
    Else
        Set ActSpace = ThisDrawing.PaperSpace
    End If

    DirTop = angle
    DirBottom = angle + dtr(180)
    DirLeft = angle + dtr(90)
    DirRigth = angle - dtr(90)

    varRet = ThisDrawing.Utility.PolarPoint(pt, DirBottom, tr.d / 2 / tr_m)
    points(0) = varRet(0)
    points(1) = varRet(1)
    varRet = ThisDrawing.Utility.PolarPoint(varRet, DirLeft, tr.f / tr_m)
    points(2) = varRet(0)
    points(3) = varRet(1)
    varRet = ThisDrawing.Utility.PolarPoint(varRet, DirTop, tr.d / tr_m)
    points(4) = varRet(0)
    points(5) = varRet(1)
    varRet = ThisDrawing.Utility.PolarPoint(varRet, DirRigth, (tr.f - tr.d1 / 2) / tr_m)
    points(6) = varRet(0)
    points(7) = varRet(1)
    varRet = ThisDrawing.Utility.PolarPoint(varRet, DirTop, (tr.H - tr.d / 2) / tr_m)
    points(8) = varRet(0)
    points(9) = varRet(1)
    varRet = ThisDrawing.Utility.PolarPoint(varRet, DirRigth, tr.d1 / tr_m)
    points(10) = varRet(0)
    points(11) = varRet(1)
    varRet = ThisDrawing.Utility.PolarPoint(varRet, DirBottom, (tr.H - tr.d / 2) / tr_m)
    points(12) = varRet(0)
    points(13) = varRet(1)
    varRet = ThisDrawing.Utility.PolarPoint(varRet, DirRigth, (tr.f - tr.d1 / 2) / tr_m)
    points(14) = varRet(0)
    points(15) = varRet(1)
    varRet = ThisDrawing.Utility.PolarPoint(varRet, DirBottom, tr.d / tr_m)
    points(16) = varRet(0)
    points(17) = varRet(1)
    points(18) = points(0)
    points(19) = points(1)
    Set pline = ActSpace.AddLightWeightPolyline(points)
    
    Dim center(0 To 2) As Double, radius As Double, StartAngle As Double, EndAngle As Double
    Dim Arc As AcadArc
    varRet = ThisDrawing.Utility.PolarPoint(pt, DirTop, tr.d / 2 / tr_m)
    center(0) = varRet(0)
    center(1) = varRet(1)
    radius = tr.d1 / 2 / tr_m
    StartAngle = DirLeft
    EndAngle = DirRigth
    Set Arc = ActSpace.AddArc(center, radius, StartAngle, EndAngle)

End Sub

Sub DrawBend(pt() As Double, angle1 As Double, angle2 As Double, Br As BendRecord, tr_m As Double, dopangle As Double)
    Dim center(0 To 2) As Double, radius As Double, StartAngle As Double, EndAngle As Double
    Dim Arc As AcadArc, arcin As AcadArc, arcout As AcadArc, varRet As Variant, a1 As Double
    Dim Line As AcadLine
    Dim ActSpace As Variant

    If ThisDrawing.ActiveSpace = acModelSpace Then
        Set ActSpace = ThisDrawing.ModelSpace
    Else
        Set ActSpace = ThisDrawing.PaperSpace
    End If
    
    If angle1 <= dtr(180) Then
        If angle2 > angle1 And angle2 < angle1 + dtr(180) Then
            varRet = ThisDrawing.Utility.PolarPoint(pt, angle1 + dtr(90), Br.R / tr_m)
            StartAngle = angle1 - dtr(90)
            EndAngle = angle1 - dtr(90) + dopangle
        Else
            varRet = ThisDrawing.Utility.PolarPoint(pt, angle1 - dtr(90), Br.R / tr_m)
            StartAngle = angle1 + (dtr(90) - dopangle)
            EndAngle = angle1 + dtr(90)
        End If
    Else
        If angle2 < angle1 And angle2 > angle1 - dtr(180) Then
            varRet = ThisDrawing.Utility.PolarPoint(pt, angle1 - dtr(90), Br.R / tr_m)
            StartAngle = angle1 + (dtr(90) - dopangle)
            EndAngle = angle1 + dtr(90)
        Else
            varRet = ThisDrawing.Utility.PolarPoint(pt, angle1 + dtr(90), Br.R / tr_m)
            StartAngle = angle1 - dtr(90)
            EndAngle = angle1 - (dtr(90) - dopangle)
        End If
    End If
    center(0) = varRet(0)
    center(1) = varRet(1)
    radius = Br.R / tr_m
    Set Arc = ActSpace.AddArc(center, radius, StartAngle, EndAngle)
    Arc.color = acRed
    radius = (Br.R - Br.d / 2) / tr_m
    Set arcin = ActSpace.AddArc(center, radius, StartAngle, EndAngle)
    radius = (Br.R + Br.d / 2) / tr_m
    Set arcout = ActSpace.AddArc(center, radius, StartAngle, EndAngle)
    Set Line = ActSpace.AddLine(arcin.StartPoint, arcout.StartPoint)
    Set Line = ActSpace.AddLine(arcin.EndPoint, arcout.EndPoint)
End Sub

Sub DrawReducer(pt() As Double, angle As Double, tr As ReducerRecord, tr_m As Double)
    Dim varRet As Variant, DirTop As Double, DirBottom As Double, DirLeft As Double, DirRigth As Double
    Dim points(0 To 9) As Double
    Dim pline As AcadLWPolyline
    Dim ActSpace As Variant

    If ThisDrawing.ActiveSpace = acModelSpace Then
        Set ActSpace = ThisDrawing.ModelSpace
    Else
        Set ActSpace = ThisDrawing.PaperSpace
    End If

    DirTop = angle
    DirBottom = angle + dtr(180)
    DirLeft = angle + dtr(90)
    DirRigth = angle - dtr(90)

    varRet = ThisDrawing.Utility.PolarPoint(pt, DirLeft, tr.d / 2 / tr_m)
    points(0) = varRet(0)
    points(1) = varRet(1)
    varRet = ThisDrawing.Utility.PolarPoint(varRet, DirTop, tr.l / tr_m)
    varRet = ThisDrawing.Utility.PolarPoint(varRet, DirRigth, (tr.d - tr.d1) / 2 / tr_m)
    points(2) = varRet(0)
    points(3) = varRet(1)
    varRet = ThisDrawing.Utility.PolarPoint(varRet, DirRigth, tr.d1 / tr_m)
    points(4) = varRet(0)
    points(5) = varRet(1)
    varRet = ThisDrawing.Utility.PolarPoint(varRet, DirBottom, tr.l / tr_m)
    varRet = ThisDrawing.Utility.PolarPoint(varRet, DirRigth, (tr.d - tr.d1) / 2 / tr_m)
    points(6) = varRet(0)
    points(7) = varRet(1)
    varRet = ThisDrawing.Utility.PolarPoint(varRet, DirLeft, tr.d / tr_m)
    points(8) = varRet(0)
    points(9) = varRet(1)
    Set pline = ActSpace.AddLightWeightPolyline(points)
    
End Sub

Sub DrawReducerBlock(pt() As Double, angle As Double, tr As ReducerRecord, tr_m As Double)
    Dim varRet As Variant, DirTop As Double, DirBottom As Double, DirLeft As Double, DirRigth As Double
    Dim points(0 To 9) As Double
    Dim s(0) As String

    DirTop = 0
    DirBottom = dtr(180)
    DirLeft = dtr(90)
    DirRigth = -dtr(90)

    varRet = ThisDrawing.Utility.PolarPoint(pt, DirLeft, tr.d / 2)
    points(0) = varRet(0)
    points(1) = varRet(1)
    varRet = ThisDrawing.Utility.PolarPoint(varRet, DirTop, tr.l)
    varRet = ThisDrawing.Utility.PolarPoint(varRet, DirRigth, (tr.d - tr.d1) / 2)
    points(2) = varRet(0)
    points(3) = varRet(1)
    varRet = ThisDrawing.Utility.PolarPoint(varRet, DirRigth, tr.d1)
    points(4) = varRet(0)
    points(5) = varRet(1)
    varRet = ThisDrawing.Utility.PolarPoint(varRet, DirBottom, tr.l)
    varRet = ThisDrawing.Utility.PolarPoint(varRet, DirRigth, (tr.d - tr.d1) / 2)
    points(6) = varRet(0)
    points(7) = varRet(1)
    varRet = ThisDrawing.Utility.PolarPoint(varRet, DirLeft, tr.d)
    points(8) = varRet(0)
    points(9) = varRet(1)
    
    s(0) = GenPlineString(points)
'    Set pline = ActSpace.AddLightWeightPolyline(points)
End Sub

Sub DrawToBlockRobot(prog() As String, BlName As String)
'рисует в блок по заданной программе
'команды: PLINE x0 y0 x1 y1 x2 y2 ...
'         ARC x0 y0 R angle1 angle2
    Dim newBlock As AcadBlock
    Dim pt0(0 To 2) As Double, p() As Double
    Dim s() As String
    Dim i As Integer, j As Integer
    Dim pline As AcadLWPolyline, arcObj As AcadArc
    Dim center(0 To 2) As Double, R As Double, ang1 As Double, ang2 As Double
    
    pt0(0) = 0: pt0(1) = 0: pt0(2) = 0
    Set newBlock = ThisDrawing.Blocks.Add(pt0, BlName)
    newBlock.origin = pt0
    
    For i = 0 To UBound(prog)
        If RegExp(prog(i), "^PLINE", True) Then
            ReDim p(0)
            s = Split(prog(i), " ")
            For j = 1 To UBound(s)
                ReDim Preserve p(j - 1)
                StrToDouble s(j), p(j - 1)
            Next j
            Set pline = newBlock.AddLightWeightPolyline(p)
        ElseIf RegExp(prog(i), "^ARC", True) Then
            s = Split(prog(i), " ")
            StrToDouble s(1), center(0)
            StrToDouble s(2), center(1)
            center(2) = 0
            StrToDouble s(3), R
            StrToDouble s(4), ang1
            StrToDouble s(5), ang2
            Set arcObj = newBlock.AddArc(center, R, ang1, ang2)
        End If
    Next i
End Sub

Sub DrawCapBlock(pt() As Double, angle As Double, tr As CapRecord, tr_m As Double)
    Dim varRet As Variant, DirTop As Double, DirBottom As Double, DirLeft As Double, DirRigth As Double
    Dim points(0 To 3) As Double, center(0 To 2) As Double, pts(0 To 3) As Double
    Dim pline As AcadLWPolyline, arcObj As AcadArc
    Dim R As Double ' радиус окружности
    Dim alpha As Double ' половина угла сектора
    Dim BlName As String
    Dim newBlock As AcadBlock
    Dim pt0(0 To 2) As Double

    BlName = GenBlockName("Cap DN" + CStr(tr.DN) + " h " + CStr(tr.k))
    If DrawExistingBlock(BlName, pt, 1 / tr_m, angle) Then
        Exit Sub
    End If
    
    Set newBlock = ThisDrawing.Blocks.Add(pt, BlName)
    
    'рисуем с поворотом 0 градусов, в точке 0,0,0 в масштабе 1:1
    DirTop = 0
    DirBottom = dtr(180)
    DirLeft = dtr(90)
    DirRigth = -dtr(90)
    pt0(0) = 0: pt0(1) = 0: pt0(2) = 0
    newBlock.origin = pt0

    varRet = ThisDrawing.Utility.PolarPoint(pt0, DirLeft, tr.d / 2)
    points(0) = varRet(0)
    points(1) = varRet(1)
    varRet = ThisDrawing.Utility.PolarPoint(pt0, DirRigth, tr.d / 2)
    points(2) = varRet(0)
    points(3) = varRet(1)
    Set pline = newBlock.AddLightWeightPolyline(points)    ' основание

    R = (tr.d ^ 2 + 4 * tr.k ^ 2) / (8 * tr.k)
    varRet = ThisDrawing.Utility.PolarPoint(pt0, DirBottom, (R - tr.k))
    center(0) = varRet(0)
    center(1) = varRet(1)
    center(2) = 0
    
    alpha = Arcsin(tr.d / 2 / R)
    
    Set arcObj = newBlock.AddArc(center, R, -alpha, alpha)

    If tr.k > tr.d / 2 Then
        pts(0) = points(0)
        pts(1) = points(1)
        varRet = ThisDrawing.Utility.PolarPoint(center, alpha, R)
        pts(2) = varRet(0)
        pts(3) = varRet(1)
        Set pline = newBlock.AddLightWeightPolyline(pts)    ' левая засечка
        
        pts(0) = points(2)
        pts(1) = points(3)
        varRet = ThisDrawing.Utility.PolarPoint(center, -alpha, R)
        pts(2) = varRet(0)
        pts(3) = varRet(1)
        Set pline = newBlock.AddLightWeightPolyline(pts)    ' правая засечка
    End If
    
    DrawExistingBlock BlName, pt, 1 / tr_m, angle
End Sub

Function GenBlockName(info As String) As String
'Формирует названия блоков
'пример: MDVb Kran 1200
    GenBlockName = "MDVb " + info
End Function

Function GetActiveSpace() As Variant
    If ThisDrawing.ActiveSpace = acModelSpace Then
        Set GetActiveSpace = ThisDrawing.ModelSpace
    Else
        Set GetActiveSpace = ThisDrawing.PaperSpace
    End If
End Function

Function DrawExistingBlock(bname As String, pt() As Double, mas As Double, angle As Double) As Boolean
    Dim blockRefObj As AcadBlockReference
    Dim i As AcadBlock
    Dim ActSpace As Variant
    
    DrawExistingBlock = False
    For Each i In ThisDrawing.Blocks
        If i.Name = bname Then
            Set ActSpace = GetActiveSpace()
            Set blockRefObj = ActSpace.InsertBlock(pt, bname, mas, mas, mas, angle)
            DrawExistingBlock = True
            Exit For
        End If
    Next i
End Function

Attribute VB_Name = "MDVvbALL"
Option Explicit
Option Base 0
'18.08.2013 Общий модуль для всех vb приложений

Public Const pi = 3.14159265358979

Public Function achar(str As String, chnum As Integer) As String
'18.08.2013 возвращает символ строки под заданным номером (номер начинается с 1)
    achar = Mid(str, chnum, 1)
End Function

Function ArcCos(X As Double) As Double
'18.08.2013 вычисляет арккосинус. параметр задавать в радианах
    ArcCos = Atn(-X / Sqr(-X * X + 1)) + 2 * Atn(1)
End Function

Function Arcsin(X As Double) As Double
'18.08.2013 вычисляет арксинуса. параметр задавать в радианах
    Arcsin = Atn(X / Sqr(-X * X + 1))
End Function

Public Function dtr(a As Double) As Double
'18.08.2013 Convert angle in degrees to radians
    dtr = (a / 180) * pi
End Function

Function Gradus(Ugol As Double)
'18.08.2013 переводит радианы в градусы. параметр задавать в радианах
    Gradus = 180 * Ugol / pi
End Function

Function MtoPK(m As Double) As String
'конвертит метраж в ПК. например 172010,5 в ПК1720+10,5
'07.09.2013 f округление до сотых метра
Dim pk As Long, met As Double
    pk = Int(m / 100)
    met = m - pk * 100
    MtoPK = "ПК" + format(pk) + "+" + format(met, "00.00")
End Function

Function Rad(Ugol As Double)
'18.08.2013 переводит градусы в радианы. параметр задавать в градусах
'TODO - использовать dtr
    Rad = pi * Ugol / 180
End Function

Public Function RegExp(strData As String, strPattern As String, Optional bolIgnoreCase As Boolean = False)
'18.08.2013 тестирует строку на регулярное выражение
Dim re As Object
    Set re = CreateObject("vbscript.regexp")
    re.Pattern = strPattern
    re.IgnoreCase = bolIgnoreCase
    If re.test(strData) Then
        RegExp = True
    Else
        RegExp = False
    End If
End Function

Public Function RegExpReplace(strData As String, strFrom As String, strTo As String, Optional bolIgnoreCase As Boolean = False, Optional bolGlobal As Boolean = True) As String
'18.08.2013 выпоняет замену в строке с помошью регулярного выражения
Dim re As Object
    Set re = CreateObject("vbscript.regexp")
    re.Pattern = strFrom
    re.IgnoreCase = bolIgnoreCase
    re.Global = bolGlobal
    RegExpReplace = re.Replace(strData, strTo)
End Function

Function StrChg(str As String, sfrom As String, sto As String) As String
'18.08.2013 выпоняет замену в строке одного символа на другой 1 раз
Dim pos As Long
    pos = InStr(str, sfrom)
    If pos = 0 Then
        StrChg = str
        Exit Function
    End If
    StrChg = Left(str, pos - 1) + sto + Mid(str, pos + Len(sfrom))
End Function

Function StrToDouble(s As String, ByRef d As Double) As Boolean
'18.08.2013 переводит строку в число, разделителем целой и дробной части может быть как . так и ,
'в случае успешного перевода возвращает true иначе false
Dim i As Integer, ch, dflag As Boolean, k As Integer, minus As Integer
dflag = False: k = 0: s = Trim(s): minus = 1: d = 0
If Left(s, 1) = "-" Then
    s = Mid(s, 2)
    minus = -1
End If
For i = 1 To Len(s)
    ch = Mid(s, i, 1)
    Select Case ch
        Case "0", "1", "2", "3", "4", "5", "6", "7", "8", "9"
            d = d * 10 + CInt(ch)
            If dflag Then k = k + 1
        Case ",", "."
            If Not dflag Then
                dflag = True
            Else
                StrToDouble = False
                Exit For
            End If
        Case Else
            StrToDouble = False
            Exit For
    End Select
    StrToDouble = True
Next i
If k > 0 Then d = d / 10 ^ k
d = d * minus
End Function

Attribute VB_Name = "Plot"
Const A4 = 1
Const A3 = 2

Sub PrintPage(format As Integer, preview As Boolean)
    Dim Layout As AcadLayout, DX As Integer, dy As Integer
    Set Layout = ThisDrawing.ModelSpace.Layout
    Layout.RefreshPlotDeviceInfo
    
    If format = A3 Then
'        Layout.ConfigName = "mdv9050.pc3"
        Layout.PlotRotation = ac90degrees
        DX = 420: dy = 297
    ElseIf format = A4 Then
'        Layout.ConfigName = "mdv9050.pc3"
        Layout.PlotRotation = ac180degrees
        DX = 210: dy = 297
    Else
        MsgBox "Неизвестный формат", vbExclamation, "Ошибка"
        Exit Sub
    End If
    

    Dim p1(0 To 1) As Double, p2(0 To 1) As Double, num As Integer, i As Integer, sp As Variant
    
    sp = ThisDrawing.Utility.GetPoint(, "Введите точку левого нижнего угла первого листа: ")
    num = InputBox("Введите число листов:", "Программа MDV", 1)
    
    Dim pline As AcadLWPolyline
    
    For i = 1 To num
        p1(0) = (i - 1) * DX + sp(0): p1(1) = 0 + sp(1)
        p2(0) = i * DX + sp(0): p2(1) = dy + sp(1)
        Layout.SetWindowToPlot p1, p2
        If preview Then
            Layout.PaperUnits = acMillimeters
            Layout.StandardScale = acVpScaleToFit
'Layout.StyleSheet = "monochrome.ctb"
            Layout.CenterPlot = True
            Layout.PlotType = acWindow
            ThisDrawing.Plot.DisplayPlotPreview acFullPreview
        Else
            Layout.PaperUnits = acMillimeters
            Layout.StandardScale = acVpScaleToFit
'           Layout.StyleSheet = "monochrome.ctb"
            Layout.CenterPlot = True
            Layout.PlotType = acWindow
            On Error Resume Next
            err.Clear
            ThisDrawing.Plot.PlotToDevice
            If err.Number <> 0 Then
                msg = "Error # " & str(err.Number) & " was generated by " _
                        & err.Source & Chr(13) & err.Description
                MsgBox msg, , "Error", err.HelpFile, err.HelpContext
            End If
        End If
    Next i
End Sub

Sub PlotA3()
    PrintPage A3, False
End Sub

Sub TestPlotA3()
    PrintPage A3, True
End Sub

Sub PlotA4()
    PrintPage A4, False
End Sub

Sub TestPlotA4()
    PrintPage A4, True
End Sub

Attribute VB_Name = "Truba"
Option Base 0
Option Explicit

Const MaxPoints = 255          'максимальное кол-во точек на трассу
Public Const MDVPath = "d:\mdvmenu\"
Const NOPK = -2
Const TextH = 2.5
Const fName = "xlsout"
Public Const MsgTitle = "Программа MDV ver. 2.30"

Type PtRec
    pk As Integer
    DX As Double
    land As Double
    pipe As Double
    deep As Double
    xcoord As Double
End Type

Type angle
    dist As Double
    uklon As Double
    Rad As Integer
    Ugol As Integer
    minutes As Integer
    tang As Double
    biss As Double
    DX As Double
    idx As Integer
End Type

Public Hscale As Double, Vscale As Double, Dpipe As Integer

Sub AcadToExcel()
'перенос отметок земли и расстояний в эксель
    Dim sset As AcadSelectionSet, status As Integer, l() As AcadEntity, numlen As Integer
    Dim oldy As Double, i As Integer, n() As AcadEntity, DX() As AcadEntity, n_num As Integer, dx_num As Integer
    Const Delta = 8 'минимальное расстояние между отметкакми земли и расстояниями м/у отметками, по вертикали
    Set sset = GetTextOnScreen
    status = 0: n_num = 0: dx_num = 0
    
    ' выбор текста
    numlen = sset.Count
    ReDim l(numlen)
    ReDim n(numlen)
    ReDim DX(numlen)
    For i = 0 To numlen - 1
        Set l(i) = sset.Item(i)
    Next i
    EntSortY l, numlen
    sset.Delete
   
    For i = 0 To numlen - 1
        If status = 0 Then
            status = 1
            oldy = EntGetY(l(i))
            Set DX(dx_num) = l(i)
            dx_num = dx_num + 1
        ElseIf status = 1 Then
            If Abs(oldy - EntGetY(l(i))) > Delta Then
                status = 2
                Set n(n_num) = l(i)
                n_num = n_num + 1
            Else
                Set DX(dx_num) = l(i)
                dx_num = dx_num + 1
            End If
        Else
            Set n(n_num) = l(i)
            n_num = n_num + 1
        End If
    Next i
    SortXandWrite DX, dx_num, "n"
    SortXandWrite n, n_num, "dx"
End Sub

'отсортировать массив по координате Х и записать в файл
Sub SortXandWrite(a() As AcadEntity, n As Integer, f As String)
Dim fnum As Integer, i As Integer
    fnum = FreeFile
    Open MDVPath + f For Output As #fnum
    EntSortX a, n
    For i = 0 To n - 1
        Write #fnum, EntD(a(i))
    Next i
    Close #fnum
End Sub

Sub LoadData()
Attribute LoadData.VB_Description = "Загрузка расчитанной в экселе трассы трубопровода"
' загрузка расчитанной трассы из текстового файла

Dim Fn As Integer, key As Integer, pts(MaxPoints) As PtRec, i As Integer, j As Integer
Dim An(MaxPoints) As angle
Dim p1(3) As Double, p2(3) As Double, p3(3) As Double
Dim pnum As Integer, Vnum As Integer
Dim Line As AcadLine
Dim oldLayer As String

If Dir(MDVPath + fName) = "" Then
    MsgBox "Не найден файл с трассой. Надо сделать экспорт трассы из Excel", vbExclamation, MsgTitle
    Exit Sub
End If

Fn = FreeFile
Open MDVPath + fName For Input Access Read As #Fn
i = 0: j = 0
Do While Not EOF(Fn) ' Цикл до конца файла.
    Input #Fn, key    ' Читает данные
    Select Case key
    Case -1
        Input #Fn, An(j).dist
        Input #Fn, An(j).uklon
        Input #Fn, An(j).Rad
        Input #Fn, An(j).Ugol
        Input #Fn, An(j).minutes
        Input #Fn, An(j).tang
        Input #Fn, An(j).biss
        Input #Fn, An(j).DX
        An(j).idx = i - 1
        j = j + 1
    Case Else
        pts(i).pk = key
        Input #Fn, pts(i).DX
        Input #Fn, pts(i).land
        Input #Fn, pts(i).pipe
        Input #Fn, pts(i).deep
        i = i + 1
    End Select
Loop
Close #Fn

pnum = i: Vnum = j

DlgOK = False
DlgNewPipe.Show
If Not DlgOK Then Exit Sub

Vscale = CDbl(DlgNewPipe.TextBox1.value) / 1000
Hscale = CDbl(DlgNewPipe.TextBox2.value) / 1000
Dpipe = CInt(DlgNewPipe.TextBox5.value)

Dim IsLandLine As Boolean, IsTrubaLine As Boolean, IsVertLine As Boolean, IsVinosk As Boolean
Dim IsPiket As Boolean, IsDist As Boolean, IsLand As Boolean, IsPipe As Boolean
Dim IsDlinaUkl As Boolean, IsDeep As Boolean

IsLandLine = DlgNewPipe.CheckBox1     '
IsTrubaLine = DlgNewPipe.CheckBox2    '
IsVertLine = DlgNewPipe.CheckBox3     '
IsVinosk = DlgNewPipe.CheckBox4       '
IsPiket = DlgNewPipe.CheckBox5        '
IsDist = DlgNewPipe.CheckBox6         '
IsLand = DlgNewPipe.CheckBox7         '
IsPipe = DlgNewPipe.CheckBox8         '
IsDlinaUkl = DlgNewPipe.CheckBox9     '
IsDeep = DlgNewPipe.CheckBox10        '

'MsgBox ("Укажите 3 точки на профиле: 1 - уровень выносок углов, 2 - левая верхняя точка уровня земли, 3 - левый верхний угол графы ПИКЕТАЖ")
MDVGetPoint p1, "Уровень выносок углов: "
MDVGetPoint p2, "Левая верхняя точка уровня земли: "
MDVGetPoint p3, "Левый верхний угол подвала: "

Dim dxold As Double, DX As Double, shift As Double, xcoord As Double, ycoord As Double
Dim txtObJ As AcadText, p(0 To 2) As Double, idx As Integer, ymas(3) As Double, xcold As Double, xnew As Double
Dim pp(0 To 2) As Double, points() As Double, lpoints() As Double

' Первая точка линии трубы
ReDim points(2)
points(0) = p2(0): points(1) = p2(1) - pts(0).deep / Vscale

shift = 0: ycoord = p3(1): idx = 0
' ymas(0) = 19: ymas(1) = 16.75: ymas(2) = 14.5
ymas(0) = 0: ymas(1) = 2.25: ymas(2) = 4.5

oldLayer = ThisDrawing.ActiveLayer.Name
Set_Layer ("lin_auto")

Dim Umode As Integer       '0 - режим S; 1 - режим У
Umode = 0
Dim UTable(0 To 1, 0 To 20) As Double 'высоты таблицы

UTable(0, 0) = ycoord - 33: UTable(1, 0) = ycoord - 61   'Пикетаж
UTable(0, 1) = ycoord - 44: UTable(1, 1) = ycoord - 55.5 'Расстояния м/у отметками
UTable(0, 2) = 2.5:         UTable(1, 2) = 2             'Высота текстовых отметок
UTable(0, 3) = ycoord - 58: UTable(1, 3) = ycoord - 19   'отметки земли
UTable(0, 4) = 1:           UTable(1, 4) = 0             'точность расстояний м/у отметками, глубина траншеи
UTable(0, 5) = 2:           UTable(1, 5) = 1             'точность отметок земли, верха трубы
UTable(0, 6) = ycoord - 73: UTable(1, 6) = ycoord - 34.9 'верх трубы
UTable(0, 7) = ycoord - 92: UTable(1, 7) = ycoord - 104  'глубина траншеи
UTable(0, 8) = ycoord - 75: UTable(1, 8) = ycoord - 44   'начало графы уклонов
UTable(0, 9) = 10:          UTable(1, 9) = 8             'высота графы уклонов
UTable(0, 10) = ycoord - 79: UTable(1, 10) = ycoord - 47 'уклон/расстояние верх
UTable(0, 11) = ycoord - 84: UTable(1, 11) = ycoord - 51 'уклон/расстояние низ
UTable(0, 12) = 4:           UTable(1, 12) = 3           'точность отметок уклонов

ReDim lpoints(pnum * 2 - 1)
'lpoints(0) = p2(0): lpoints(1) = p2(1)

' отрисовка в цикле отметок подвала
For i = 0 To pnum - 1
    dxold = DX
    DX = pts(i).DX
    shift = shift + DX
    xcoord = p3(0) + shift / Hscale
    pts(i).xcoord = xcoord
    
    ' если в точке целый пикет - отрисовать
    If IsPiket And pts(i).pk <> NOPK Then
        p(0) = xcoord: p(1) = UTable(Umode, 0): p(2) = 0
        Set txtObJ = PutText(Trim(str(pts(i).pk)), UTable(Umode, 2), p, acAlignmentCenter, 0)
    End If
    
    ' рисуем растояния м/у отметками
    If shift <> 0 Then
        ' вертикально раздвигаем отметки
        If (pts(i).DX + dxold) / Hscale / 2 <= 4 Then
            idx = idx + 1
            If idx > 2 Then idx = 0
        Else
            idx = 0
        End If
        p(0) = xcoord - DX / Hscale / 2: p(1) = UTable(Umode, 1) + ymas(idx): p(2) = 0
        If Umode = 0 And pts(i).DX <> 100 Then
            If IsDist Then Set txtObJ = PutTextPF(pts(i).DX, UTable(Umode, 4), 2, p, acAlignmentCenter, 0)
            If IsVertLine Then
                p(0) = xcoord - DX / Hscale: p(1) = ycoord - 35
                pp(0) = p(0): pp(1) = ycoord - 37
                ' засечка м/у растояниями
                Set Line = ThisDrawing.ModelSpace.AddLine(p, pp)
                p(1) = ycoord: pp(1) = p2(1) + (pts(i - 1).land - pts(0).land - 6) / Vscale
                ' линия от подвала к земле
                Set Line = ThisDrawing.ModelSpace.AddLine(p, pp)
            End If
        ElseIf Umode = 1 Then
            If IsDist Then Set txtObJ = PutTextPF(pts(i).DX, UTable(Umode, 4), 2, p, acAlignmentCenter, 0)
            p(0) = xcoord - DX / Hscale: p(1) = ycoord - 52
            pp(0) = p(0): pp(1) = ycoord - 57
            If IsDist Then Set Line = ThisDrawing.ModelSpace.AddLine(p, pp)
            If IsVertLine Then
                p(1) = ycoord: pp(1) = p2(1) + (pts(i - 1).land - pts(0).land - 6) / Vscale
                Set Line = ThisDrawing.ModelSpace.AddLine(p, pp)
            End If
        End If
    Else
        idx = 0
    End If
    ' раздвигаем горизонтально
    xnew = xcoord
    If xnew - xcold < 2.55 Then xnew = xcold + 2.55
    
    ' отметки земли
    p(0) = xnew: p(1) = UTable(Umode, 3): p(2) = 0
    If IsLand Then Set txtObJ = PutTextPF(pts(i).land, UTable(Umode, 5), UTable(Umode, 2), p, acAlignmentMiddleLeft, 90)
    lpoints(i * 2) = xcoord: lpoints(i * 2 + 1) = (pts(i).land - pts(0).land) / Vscale + p2(1)
    
    ' верх трубы
    p(1) = UTable(Umode, 6)
    If IsPipe Then Set txtObJ = PutTextPF(pts(i).pipe, UTable(Umode, 5), UTable(Umode, 2), p, acAlignmentMiddleLeft, 90)

    ' глубина траншеи
    p(1) = UTable(Umode, 7)
    If IsDeep Then Set txtObJ = PutTextPF(pts(i).deep, UTable(Umode, 4), UTable(Umode, 2), p, acAlignmentMiddleLeft, 90)
    
    xcold = xnew
Next i

For i = 0 To Vnum - 1
    ' перемычка
    xcoord = pts(An(i).idx).xcoord
    
    If IsDlinaUkl Then
        p(0) = xcoord: p(1) = UTable(Umode, 8): p(2) = 0#
        pp(0) = xcoord: pp(1) = p(1) - UTable(Umode, 9): pp(2) = 0#
        Set Line = ThisDrawing.ModelSpace.AddLine(p, pp)
        ' уклон и растояние слева от точки format mid
        If An(i).uklon > 0 Then
            p(0) = 2 + xcoord - An(i).dist / Hscale: p(1) = UTable(Umode, 10): p(2) = 0
            Set txtObJ = PutTextPF(An(i).uklon, UTable(Umode, 12), UTable(Umode, 2), p, acAlignmentLeft, 0)
            p(0) = xcoord - 2: p(1) = UTable(Umode, 11)
            Set txtObJ = PutTextPF(An(i).dist, UTable(Umode, 4), UTable(Umode, 2), p, acAlignmentRight, 0)
            p(0) = xcoord: p(1) = UTable(Umode, 8): p(2) = 0#
            pp(0) = xcoord - An(i).dist / Hscale: pp(1) = p(1) - UTable(Umode, 9): pp(2) = 0#
        ElseIf An(i).uklon < 0 Then
            p(0) = xcoord - 2: p(1) = UTable(Umode, 10): p(2) = 0
            Set txtObJ = PutTextPF(An(i).uklon * (-1), UTable(Umode, 12), UTable(Umode, 2), p, acAlignmentRight, 0)
            p(0) = 2 + xcoord - An(i).dist / Hscale: p(1) = UTable(Umode, 11)
            Set txtObJ = PutTextPF(An(i).dist, UTable(Umode, 4), UTable(Umode, 2), p, acAlignmentLeft, 0)
            p(0) = xcoord: p(1) = UTable(Umode, 8): p(2) = 0#
            pp(0) = xcoord - An(i).dist / Hscale: pp(1) = p(1) - UTable(Umode, 9): pp(2) = 0#
        Else
            p(0) = xcoord - An(i).dist / Hscale / 2: p(1) = UTable(Umode, 10): p(2) = 0
            Set txtObJ = PutTextPF(An(i).uklon, UTable(Umode, 12), UTable(Umode, 2), p, acAlignmentCenter, 0)
            p(1) = UTable(Umode, 11)
            Set txtObJ = PutTextPF(An(i).dist, UTable(Umode, 4), UTable(Umode, 2), p, acAlignmentCenter, 0)
            p(0) = xcoord: p(1) = UTable(Umode, 8) - UTable(Umode, 9) / 2: p(2) = 0#
            pp(0) = xcoord - An(i).dist / Hscale: pp(1) = p(1): pp(2) = 0#
        End If
        Set Line = ThisDrawing.ModelSpace.AddLine(p, pp)
    End If
    
    If IsVinosk Then
        ' полка с росписью вертикального угла
        p(0) = xcoord: p(1) = p1(1): p(2) = 0
        pp(0) = p(0): pp(1) = p1(1) + 30: pp(2) = p(2)
        Set Line = ThisDrawing.ModelSpace.AddLine(p, pp)
        If An(i).biss < 0 Then
            CopyPt pp, p
            pp(0) = pp(0) + 20
        Else
            CopyPt p, pp
            pp(0) = pp(0) + 20
        End If
        Set Line = ThisDrawing.ModelSpace.AddLine(p, pp)
        p(0) = xcoord + 1.5: p(1) = p1(1) + 30 - 4: p(2) = 0
        Set txtObJ = PutText("Уг" + Trim(str(An(i).Ugol)) + "%%d" + format(An(i).minutes, "00") + "'", TextH, p, acAlignmentLeft, 0)
        p(1) = p(1) - 4.5
        Set txtObJ = PutText("R=" + Trim(str(An(i).Rad)) + "м", TextH, p, acAlignmentLeft, 0)
        p(1) = p(1) - 4.5
        Set txtObJ = PutTextP("T=" + format(An(i).tang, "0.00") + "м", TextH, p, acAlignmentLeft, 0)
        p(1) = p(1) - 4.5
        Set txtObJ = PutTextP("Б=" + format(An(i).biss, "0.00") + "м", TextH, p, acAlignmentLeft, 0)
        p(1) = p(1) - 4.5
        Set txtObJ = PutText("Вуг=" + Trim(str(pts(An(i).idx).pipe)), TextH, p, acAlignmentLeft, 0)
        p(1) = p(1) - 4.5
        Dim myStr As String
        myStr = StrChg(Trim(format(An(i).DX, ".000")), ",", "+")
        myStr = Mid(myStr, 1, Len(myStr) - 1) + "." + Mid(myStr, Len(myStr))
        Set txtObJ = PutText("ПК" + myStr, TextH, p, acAlignmentLeft, 0)
    End If
    
    ReDim Preserve points(i * 2 + 3)
    points(i * 2 + 2) = xcoord: points(i * 2 + 3) = p2(1) + ((pts(An(i).idx).land - pts(An(i).idx).deep - pts(0).land) / Vscale)
Next i

' отрисовка трубы
Dim plineObj As AcadLWPolyline, plineObj2 As AcadLWPolyline

If IsLandLine Then
    Set plineObj = ThisDrawing.ModelSpace.AddLightWeightPolyline(lpoints)
End If

If IsTrubaLine Then
    Set plineObj = ThisDrawing.ModelSpace.AddLightWeightPolyline(points)
    plineObj.Lineweight = acLnWt050
    ' труба (для ДУ=700 и более - в 2 линии)
    If Dpipe > 630 Then
        Set plineObj2 = plineObj.Copy
        p(0) = 0: p(1) = 0: p(2) = 0
        CopyPt p, pp
        pp(1) = pp(1) + Dpipe / Vscale / 1000
        plineObj2.Move p, pp
    End If
End If

Set_Layer (oldLayer)
ThisDrawing.Regen acActiveViewport

End Sub

Sub LandToFile()
'Сканирует линию земли и переносит ее в файл для экспорта в эксель
Dim H As Double, ScaleX As Integer, ScaleY As Integer
    DlgExpLine.Show
    If DlgOK = False Then Exit Sub
    
    StrToDouble DlgExpLine.TextBox1.text, H
    ScaleX = DlgExpLine.TextBox2.value
    ScaleY = DlgExpLine.TextBox3.value
    
    Const fNameN = "n"
    Const fNameDX = "dx"
    Dim sset As AcadSelectionSet, i As Integer, entry As AcadEntity, retCoord As Variant
    Dim FnN As Integer, FnDX As Integer
    Set sset = GetSelSet("mdv1")
    Dim FilterType(0) As Integer
    Dim FilterData(0) As Variant
    FilterType(0) = 0
    FilterData(0) = "LWPolyline"
    sset.SelectOnScreen FilterType, FilterData
    
    Set entry = sset.Item(0)
    retCoord = entry.Coordinates
    FnN = FreeFile
    Open MDVPath + fNameN For Output As #FnN
    FnDX = FreeFile
    Open MDVPath + fNameDX For Output As #FnDX
    i = 1
    While i <= UBound(retCoord)
        ' запись расчитанной трассы в текстовый файл
        Write #FnN, (retCoord(i) - retCoord(1)) * ScaleY / 1000 + H
        i = i + 1
        On Error Resume Next
        Write #FnDX, (retCoord(i) - retCoord(i - 2)) * ScaleX / 1000
        i = i + 1
    Wend
    Close #FnN
    Close #FnDX
    sset.Delete
End Sub

Sub Skvajina()
DlgSkv.Show
If DlgOK = False Then Exit Sub
Dim deeps(5) As Double, dcount As Integer, Vscale As Integer
Dim p1(0 To 2) As Double, p2(0 To 2) As Double
Dim Line As AcadLine, i As Integer, txtObJ As AcadText, pObj As AcadPoint

Vscale = CInt(DlgSkv.TextBox6)
dcount = 0

If DlgSkv.TextBox1.value <> "" Then
    deeps(dcount) = DlgSkv.TextBox1.value
    dcount = dcount + 1
End If
If DlgSkv.TextBox2.value <> "" Then
    deeps(dcount) = DlgSkv.TextBox2.value
    dcount = dcount + 1
End If
If DlgSkv.TextBox3.value <> "" Then
    deeps(dcount) = DlgSkv.TextBox3.value
    dcount = dcount + 1
End If
If DlgSkv.TextBox4.value <> "" Then
    deeps(dcount) = DlgSkv.TextBox4.value
    dcount = dcount + 1
End If
If DlgSkv.TextBox5.value <> "" Then
    deeps(dcount) = DlgSkv.TextBox5.value
    dcount = dcount + 1
End If

MDVGetPoint p1, "Точка вставки: "

For i = 0 To dcount - 1
    p2(0) = p1(0) + 1: p2(1) = p1(1) - deeps(i) / Vscale * 1000 - 0.75
    Set txtObJ = PutTextPF(deeps(i), 1, 1.5, p2, acAlignmentLeft, 0)
    txtObJ.ScaleFactor = 0.77
    p2(0) = p1(0): p2(1) = p1(1) - deeps(i) / Vscale * 1000
    Set pObj = ThisDrawing.ModelSpace.AddPoint(p2)
Next i

p2(0) = p1(0): p2(1) = p1(1) - deeps(dcount - 1) / Vscale * 1000
Set Line = ThisDrawing.ModelSpace.AddLine(p1, p2)
p1(0) = p1(0) - 1: p1(1) = p2(1): p2(0) = p2(0) + 1
Set Line = ThisDrawing.ModelSpace.AddLine(p1, p2)

End Sub


Sub SkvVK()
'отрисовка скважины по таблицам изысканий
    Dim sset As AcadSelectionSet
    Dim FilterType(0) As Integer
    Dim FilterData(0) As Variant
    Dim l() As AcadEntity
    Dim SkvNum As String, OtmUst As String, numlen As Integer, i As Integer, BaseX As Double, BaseY As Double
    Dim X As Double
    Dim dh(40) As Double, dhn As Integer
    Dim raz(40) As String, razn As Integer
    Dim pline As AcadLWPolyline, hat As AcadHatch
    Dim points(0 To 9) As Double, d As Double, p(0 To 5) As Double, pt(0 To 2) As Double, p2(0 To 3) As Double
    Dim outerLoop(0 To 0) As AcadEntity, txt As AcadText, GrVod As String, ur As Double

    Const DX1 = -52, dx2 = -21.7, dx3 = 74.5, Delta = 3, m = 100
    
    dhn = 0: razn = 0: GrVod = ""
    ' выбор шапки скважины и таблицы
    Set sset = GetSelSet("mdv")
    FilterType(0) = 0
    FilterData(0) = "text"
    sset.SelectOnScreen FilterType, FilterData
    numlen = sset.Count
    ReDim l(numlen)
    For i = 0 To numlen - 1
        Set l(i) = sset.Item(i)
        If RegExp(l(i).TextString, "Скважина ") Then
            SkvNum = Mid(l(i).TextString, 10)
            BaseX = EntGetX(l(i))
            BaseY = EntGetY(l(i))
        End If
        If RegExp(l(i).TextString, "высотная отметка устья ") Then
            OtmUst = Mid(l(i).TextString, 25)
            OtmUst = RegExpReplace(OtmUst, " м.", "")
        End If
    Next i
    sset.Delete
    EntSortY l, numlen
    For i = numlen - 1 To 0 Step -1
        X = EntGetX(l(i))
        If X < BaseX + DX1 + Delta And X > BaseX + DX1 - Delta And RegExp(l(i).TextString, "\d+") Then
            StrToDouble l(i).TextString, d
            dh(dhn) = d
            dhn = dhn + 1
        ElseIf X < BaseX + dx2 + Delta And X > BaseX + dx2 - Delta And RegExp(l(i).TextString, "\d+") Then
            raz(razn) = l(i).TextString
            razn = razn + 1
        ElseIf X < BaseX + dx3 + Delta And X > BaseX + dx3 - Delta And RegExp(l(i).TextString, "\d+") Then
            GrVod = l(i).TextString
        End If
    Next i
    p(0) = BaseX + 130 + 5: p(1) = BaseY
    p(2) = p(0): p(3) = p(1) + 10
    p(4) = p(2) + 16: p(5) = p(3)
    Set pline = ThisDrawing.PaperSpace.AddLightWeightPolyline(p)
    pt(0) = p(2) + 2: pt(1) = p(5) + 0.5
    Set txt = PutTextPaper("скв. " + SkvNum, 2.5, pt, acAlignmentLeft, 0)
    pt(0) = p(2) + 2: pt(1) = p(5) - 3.5
    Set txt = PutTextPaper(OtmUst, 2.5, pt, acAlignmentLeft, 0)
    If GrVod <> "" Then
        StrToDouble GrVod, ur
        p2(0) = BaseX + 130: p2(1) = BaseY - ur * 1000 / m
        p2(2) = p2(0) - 16: p2(3) = p2(1)
        Set pline = ThisDrawing.PaperSpace.AddLightWeightPolyline(p2)
        p(0) = p2(0) - 8: p(1) = p2(1)
        p(2) = p(0): p(3) = p(1) - 7
        p(4) = p(2) - 10: p(5) = p(3)
        Set pline = ThisDrawing.PaperSpace.AddLightWeightPolyline(p)
        pt(0) = p(4) + 0.5: pt(1) = p(5) + 1
        Set txt = PutTextPaper("У.Г.В.", 2.5, pt, acAlignmentLeft, 0)
        p(0) = p(0) - 2.12: p(1) = p(1) - 2.12
        p(2) = p(0) + 2.12: p(3) = p(1) + 2.12
        p(4) = p(2) + 2.12: p(5) = p(3) - 2.12
        Set pline = ThisDrawing.PaperSpace.AddLightWeightPolyline(p)
    End If
    For i = 0 To dhn - 1
        points(0) = BaseX + 130: points(1) = BaseY
        points(2) = points(0) + 10: points(3) = points(1)
        points(4) = points(2): points(5) = points(3) - dh(i) * 1000 / m
        points(6) = points(0): points(7) = points(5)
        points(8) = points(0): points(9) = points(1)
        Set pline = ThisDrawing.PaperSpace.AddLightWeightPolyline(points)
        Set outerLoop(0) = pline
        BaseY = points(7)
        If RegExp(raz(i), "^11[бв]") Then
            Set hat = ThisDrawing.PaperSpace.AddHatch(acHatchPatternTypePreDefined, "DOTS", True)
            hat.AppendOuterLoop (outerLoop)
            hat.Evaluate
        ElseIf RegExp(raz(i), "^22") Then
            Set hat = ThisDrawing.PaperSpace.AddHatch(acHatchPatternTypePreDefined, "LINE", True)
            hat.AppendOuterLoop (outerLoop)
            hat.Evaluate
        ElseIf RegExp(raz(i), "^21") Then
            Set hat = ThisDrawing.PaperSpace.AddHatch(acHatchPatternTypePreDefined, "ANSI31", True)
            hat.AppendOuterLoop (outerLoop)
            hat.Evaluate
        ElseIf RegExp(raz(i), "^17") Then
            Set hat = ThisDrawing.PaperSpace.AddHatch(acHatchPatternTypeCustomDefined, "34", True)
            hat.AppendOuterLoop (outerLoop)
            hat.PatternScale = 5
            hat.Evaluate
        ElseIf RegExp(raz(i), "^12") Then
            Set hat = ThisDrawing.PaperSpace.AddHatch(acHatchPatternTypeCustomDefined, "33", True)
            hat.AppendOuterLoop (outerLoop)
            hat.PatternScale = 5
            hat.Evaluate
        ElseIf RegExp(raz(i), "^18") Then
            Set hat = ThisDrawing.PaperSpace.AddHatch(acHatchPatternTypeCustomDefined, "34", True)
            hat.AppendOuterLoop (outerLoop)
            hat.PatternScale = 5
            hat.PatternAngle = Rad(-45)
            hat.Evaluate
        ElseIf RegExp(raz(i), "^11") Then
            Set hat = ThisDrawing.PaperSpace.AddHatch(acHatchPatternTypeCustomDefined, "10", True)
            hat.AppendOuterLoop (outerLoop)
            hat.PatternScale = 5
            hat.Evaluate
        ElseIf RegExp(raz(i), "^15") Then
            Set hat = ThisDrawing.PaperSpace.AddHatch(acHatchPatternTypePreDefined, "DOTS", True)
            hat.AppendOuterLoop (outerLoop)
            hat.Evaluate
        ElseIf RegExp(raz(i), "^1") Then
            Set hat = ThisDrawing.PaperSpace.AddHatch(acHatchPatternTypePreDefined, "ANSI37", True)
            hat.AppendOuterLoop (outerLoop)
            hat.Evaluate
        End If
    Next i
    ThisDrawing.Regen True
End Sub

Sub Kolodez()
    Dim points(0 To 9) As Double, klen As Double, pt(0 To 2) As Double, pt2(0 To 2) As Double, pp(0 To 3) As Double
    Dim pline As AcadLWPolyline
    klen = CDbl(InputBox("Введите ширину колодца в мм чертежа:", , 2))
    MDVGetPoint pt, "Верх колодца: "
    MDVGetPointDir pt2, pt, "Низ колодца: "
    points(0) = pt(0) - klen / 2: points(1) = pt(1) + 1.5
    points(2) = points(0) + klen: points(3) = points(1)
    points(4) = points(2): points(5) = pt2(1) - 2
    points(6) = points(0): points(7) = points(5)
    points(8) = points(0): points(9) = points(1)
    Set pline = ThisDrawing.ModelSpace.AddLightWeightPolyline(points)
    pp(0) = points(6) - 1: pp(1) = points(7)
    pp(2) = points(4) + 1: pp(3) = pp(1)
    Set pline = ThisDrawing.ModelSpace.AddLightWeightPolyline(pp)
    pline.Lineweight = acLnWt025
End Sub

Sub Futlar()
    Dim points(0 To 7) As Double, pt(0 To 2) As Double, pt2(0 To 2) As Double, p(0 To 5) As Double
    Dim pline As AcadLWPolyline, txt As AcadText
    MDVGetPoint pt, "Начало: "
    MDVGetPointDir pt2, pt, "Конец: "
    points(0) = pt(0): points(1) = pt(1) + 2
    points(2) = points(0): points(3) = points(1) - 1
    points(4) = pt2(0): points(5) = pt2(1) + 1
    points(6) = points(4): points(7) = points(5) + 1
    Set pline = ThisDrawing.ModelSpace.AddLightWeightPolyline(points)
    points(0) = pt(0): points(1) = pt(1) - 2
    points(2) = points(0): points(3) = points(1) + 1
    points(4) = pt2(0): points(5) = pt2(1) - 1
    points(6) = points(4): points(7) = points(5) - 1
    Set pline = ThisDrawing.ModelSpace.AddLightWeightPolyline(points)
    p(0) = (points(2) + points(4)) / 2: p(1) = (points(3) + points(5)) / 2
    p(2) = p(0) - 7: p(3) = p(1) - 12
    p(4) = p(2) - 28: p(5) = p(3)
    Set pline = ThisDrawing.ModelSpace.AddLightWeightPolyline(p)
    pt(0) = p(4): pt(1) = p(5) + 1
    Set txt = PutText("Футляр из трубы", 2.5, pt, acAlignmentLeft, 0)
    pt(0) = p(4): pt(1) = p(5) - 4
    Set txt = PutText("%%c999x99,9; L=9,99", 2.5, pt, acAlignmentLeft, 0)
End Sub

Sub LoadDataVK()
' загрузка расчитанной трассы из текстового файла
'07.09.2013 - + таблица для НИИПИнефтегазстроймаш,
'             f запрет вывода нулевых расстояний
'             + 2 поля в таблицу начало и высота засечки между расстояниями
'             f перевод в пикеты через MtoPK
'22.06.2015 - f таблица вывода по умолчанию - ВНИИГАЗ-ГАЗ
'             f вывод трубы по отметкам трубы а не дна траншеи
'27.10.2015 - f не выводи 0 расстояния
'             f 0 уклоны округляем до 1 знака
'             f не выводим 90 градусные уклоны (10000)

Dim Fn As Integer, key As Integer, pts(MaxPoints) As PtRec, i As Integer, j As Integer
Dim An(MaxPoints) As angle
Dim p1(3) As Double, p2(3) As Double, p3(3) As Double
Dim pnum As Integer, Vnum As Integer
Dim Line As AcadLine
Dim oldLayer As String, TrbName As String
Dim Umode As Integer       '0 - наш режим; 1 - режим ВК; 2 - режим Промнефтегазэкология; 3 - режим Промнефтегазэкология; 4-НИИПИнефтегазстроймаш
Dim DS As Object
Dim NizTrubi As Boolean

NizTrubi = False 'по умолчанию отметки верха трубы

If ThisDrawing.ActiveSpace = acModelSpace Then
    Set DS = ThisDrawing.ModelSpace
Else
    Set DS = ThisDrawing.PaperSpace
End If

If Dir(MDVPath + fName) = "" Then
    MsgBox "Не найден файл с трассой. Надо сделать экспорт трассы из Excel", vbExclamation, MsgTitle
    Exit Sub
End If

Fn = FreeFile
Open MDVPath + fName For Input Access Read As #Fn
i = 0: j = 0
Do While Not EOF(Fn) ' Цикл до конца файла.
    Input #Fn, key    ' Читает данные
    Select Case key
    Case -1
        Input #Fn, An(j).dist
        Input #Fn, An(j).uklon
        Input #Fn, An(j).Rad
        Input #Fn, An(j).Ugol
        Input #Fn, An(j).minutes
        Input #Fn, An(j).tang
        Input #Fn, An(j).biss
        Input #Fn, An(j).DX
        An(j).idx = i - 1
        j = j + 1
    Case -3
        Input #Fn, TrbName
        NizTrubi = True  'отметки даны по низу трубы
    Case Else
        pts(i).pk = key
        Input #Fn, pts(i).DX
        Input #Fn, pts(i).land
        Input #Fn, pts(i).pipe
        Input #Fn, pts(i).deep
        i = i + 1
    End Select
Loop
Close #Fn

pnum = i: Vnum = j

DlgOK = False
DlgNewPipe.ComboBox1.Clear
DlgNewPipe.ComboBox1.AddItem ("ВНИИГАЗ-ГАЗ")
DlgNewPipe.ComboBox1.AddItem ("ВНИИГАЗ-ВК")
DlgNewPipe.ComboBox1.AddItem ("Промнефтегазэкология")
DlgNewPipe.ComboBox1.AddItem ("Промнефтегазэкология укрупненный")
DlgNewPipe.ComboBox1.AddItem ("НИИПИнефтегазстроймаш")
DlgNewPipe.ComboBox1.ListIndex = 0
DlgNewPipe.Show
If Not DlgOK Then Exit Sub

Umode = DlgNewPipe.ComboBox1.ListIndex
Vscale = CDbl(DlgNewPipe.TextBox1.value) / 1000
Hscale = CDbl(DlgNewPipe.TextBox2.value) / 1000
Dpipe = CInt(DlgNewPipe.TextBox5.value)

Dim IsLandLine As Boolean, IsTrubaLine As Boolean, IsVertLine As Boolean, IsVinosk As Boolean
Dim IsPiket As Boolean, IsDist As Boolean, IsLand As Boolean, IsPipe As Boolean
Dim IsDlinaUkl As Boolean, IsDeep As Boolean

IsLandLine = DlgNewPipe.CheckBox1     '
IsTrubaLine = DlgNewPipe.CheckBox2    '
IsVertLine = DlgNewPipe.CheckBox3     '
IsVinosk = DlgNewPipe.CheckBox4       '
IsPiket = DlgNewPipe.CheckBox5        '
IsDist = DlgNewPipe.CheckBox6         '
IsLand = DlgNewPipe.CheckBox7         '
IsPipe = DlgNewPipe.CheckBox8         '
IsDlinaUkl = DlgNewPipe.CheckBox9     '
IsDeep = DlgNewPipe.CheckBox10        '

'MsgBox ("Укажите 3 точки на профиле: 1 - уровень выносок углов, 2 - левая верхняя точка уровня земли, 3 - левый верхний угол графы ПИКЕТАЖ")
MDVGetPoint p1, "Уровень выносок углов/глубины траншеи(для режима ВК): "
MDVGetPoint p2, "Левая верхняя точка уровня земли: "
MDVGetPoint p3, "Левый верхний угол подвала: "

Dim dxold As Double, DX As Double, shift As Double, xcoord As Double, ycoord As Double
Dim txtObJ As AcadText, p(0 To 2) As Double, idx As Integer, ymas(3) As Double, xcold As Double, xnew As Double
Dim pp(0 To 2) As Double, points() As Double, lpoints() As Double

' Первая точка линии трубы
ReDim points(2)
' points(0) = p2(0): points(1) = p2(1) - pts(0).deep / Vscale
points(0) = p2(0): points(1) = p2(1) + ((pts(0).pipe - pts(0).land) / Vscale)

shift = 0: ycoord = p3(1): idx = 0
' ymas(0) = 19: ymas(1) = 16.75: ymas(2) = 14.5
ymas(0) = 0: ymas(1) = 2.25: ymas(2) = 4.5

oldLayer = ThisDrawing.ActiveLayer.Name
Set_Layer ("lin_auto")

Dim UTable(0 To 4, 0 To 16) As Double 'описания таблиц

UTable(0, 0) = ycoord - 33: UTable(1, 0) = ycoord - 130:  UTable(2, 0) = ycoord - 178.3 'Пикетаж
UTable(0, 1) = ycoord - 40: UTable(1, 1) = ycoord - 85.3: UTable(2, 1) = ycoord - 168#   'Расстояния м/у отметками
UTable(0, 2) = 2.5:         UTable(1, 2) = 2.5:           UTable(2, 2) = 2.5            'Высота текстовых отметок
UTable(0, 3) = ycoord - 58: UTable(1, 3) = ycoord - 26.9: UTable(2, 3) = ycoord - 82    'отметки земли
UTable(0, 4) = 2:           UTable(1, 4) = 2:             UTable(2, 4) = 2              'точность расстояний м/у отметками, глубина траншеи
UTable(0, 5) = 2:           UTable(1, 5) = 3:             UTable(2, 5) = 2              'точность отметок земли, верха трубы
UTable(0, 6) = ycoord - 73: UTable(1, 6) = ycoord - 12.9: UTable(2, 6) = ycoord - 70.8  'верх трубы
UTable(0, 7) = ycoord - 92: UTable(1, 7) = p1(1):         UTable(2, 7) = ycoord - 100.4 'глубина траншеи
UTable(0, 8) = ycoord - 75: UTable(1, 8) = ycoord - 70:   UTable(2, 8) = ycoord - 154   'начало графы уклонов
UTable(0, 9) = 10:          UTable(1, 9) = 10:            UTable(2, 9) = 9              'высота графы уклонов
UTable(0, 10) = ycoord - 79: UTable(1, 10) = ycoord - 73.7: UTable(2, 10) = ycoord - 158 'уклон/расстояние верх
UTable(0, 11) = ycoord - 84: UTable(1, 11) = ycoord - 79.1: UTable(2, 11) = ycoord - 162.4 'уклон/расстояние низ
UTable(0, 12) = 4:           UTable(1, 12) = 1:           UTable(2, 12) = 4             'точность отметок уклонов
UTable(0, 13) = 1:           UTable(1, 13) = 0:           UTable(2, 13) = 1             'рисовать выноску углов
UTable(0, 14) = 1:          UTable(1, 14) = 1000:         UTable(2, 14) = 1000:            'к-т уклона
UTable(0, 15) = 0:          UTable(1, 15) = 0:            UTable(2, 15) = 173:            'низ засечки между растояниями
UTable(0, 16) = 0:          UTable(1, 16) = 0:            UTable(2, 16) = 2.5:            'высота засечки между растояниями

UTable(3, 0) = UTable(2, 0) + 50: UTable(4, 0) = ycoord - 175.85
UTable(3, 1) = UTable(2, 1) + 50: UTable(4, 1) = ycoord - 165.85
UTable(3, 2) = UTable(2, 2):      UTable(4, 2) = 2.5
UTable(3, 3) = UTable(2, 3) + 50: UTable(4, 3) = ycoord - 36.57
UTable(3, 4) = UTable(2, 4):      UTable(4, 4) = 2
UTable(3, 5) = UTable(2, 5):      UTable(4, 5) = 2
UTable(3, 6) = UTable(2, 6) + 50: UTable(4, 6) = ycoord - 53.4
UTable(3, 7) = UTable(2, 7) + 50: UTable(4, 7) = ycoord - 64.06
UTable(3, 8) = UTable(2, 8) + 50: UTable(4, 8) = ycoord - 150
UTable(3, 9) = UTable(2, 9):      UTable(4, 9) = 10
UTable(3, 10) = UTable(2, 10) + 50: UTable(4, 10) = ycoord - 153.14
UTable(3, 11) = UTable(2, 11) + 50: UTable(4, 11) = ycoord - 159.23
UTable(3, 12) = UTable(2, 12):    UTable(4, 12) = 4
UTable(3, 13) = UTable(2, 13):    UTable(4, 13) = 1
UTable(3, 14) = UTable(2, 14):    UTable(4, 14) = 1
UTable(4, 15) = UTable(2, 15) + 50: UTable(4, 15) = ycoord - 170
UTable(4, 16) = 2.5:                UTable(4, 16) = 10

ReDim lpoints(pnum * 2 - 1)
'lpoints(0) = p2(0): lpoints(1) = p2(1)

xcold = p3(0) - 10

' отрисовка в цикле отметок подвала
For i = 0 To pnum - 1
    dxold = DX
    DX = pts(i).DX
    shift = shift + DX
    xcoord = p3(0) + shift / Hscale
    pts(i).xcoord = xcoord
    
    ' если в точке целый пикет - отрисовать
    If IsPiket And pts(i).pk <> NOPK Then
        p(0) = xcoord: p(1) = UTable(Umode, 0): p(2) = 0
        Set txtObJ = PutText(Trim(str(pts(i).pk)), UTable(Umode, 2), p, acAlignmentCenter, 0)
    End If
    
    ' рисуем растояния м/у отметками
    p(0) = xcoord - DX / Hscale / 2: p(1) = UTable(Umode, 1): p(2) = 0
    If IsDist And pts(i).DX > 0 Then Set txtObJ = PutTextPF(pts(i).DX, UTable(Umode, 4), 2.5, p, acAlignmentMiddle, IIf(pts(i).DX < 32 / Hscale, 90, 0))
    If IsVertLine Then
        p(0) = xcoord - DX / Hscale: p(1) = p3(1) - UTable(Umode, 15)
        pp(0) = p(0): pp(1) = p(1) + UTable(Umode, 16)
        ' засечка м/у растояниями
        Set Line = DS.AddLine(p, pp)
        'p(1) = ycoord: pp(1) = p2(1) + (pts(i - 1).land - pts(0).land - 6) / Vscale
        ' линия от подвала к земле
        'Set Line = ds.AddLine(p, pp)
    End If
    ' раздвигаем горизонтально
    xnew = xcoord
    If xnew - xcold < 2.55 Then xnew = xcold + 2.55
    
    ' отметки земли
    p(0) = xnew: p(1) = UTable(Umode, 3): p(2) = 0
    If IsLand Then Set txtObJ = PutTextPF(pts(i).land, UTable(Umode, 5), UTable(Umode, 2), p, acAlignmentMiddleLeft, 90)
    lpoints(i * 2) = xcoord: lpoints(i * 2 + 1) = (pts(i).land - pts(0).land) / Vscale + p2(1)
    
    ' верх трубы
    p(1) = UTable(Umode, 6)
    If IsPipe Then Set txtObJ = PutTextPF(pts(i).pipe, UTable(Umode, 5), UTable(Umode, 2), p, acAlignmentMiddleLeft, 90)

    ' глубина траншеи
    p(1) = UTable(Umode, 7)
    If IsDeep And pts(i).deep > 0 Then
        Set txtObJ = PutTextPF(pts(i).deep, UTable(Umode, 4), UTable(Umode, 2), p, acAlignmentMiddleLeft, 90)
        If Umode = 1 Then
            p(1) = p(1) - 2
            pp(0) = p(0): pp(1) = p2(1) + (pts(i).land - pts(0).land) / Vscale
            Set Line = DS.AddLine(p, pp)
        End If
    End If
    
    xcold = xnew
Next i

If TrbName <> "" Then
    p(0) = (p3(0) + xnew) / 2: p(1) = ycoord - 54: p(2) = 0
    Set txtObJ = PutText(TrbName, UTable(Umode, 2), p, acAlignmentCenter, 0)
End If

For i = 0 To Vnum - 1
    ' перемычка
    xcoord = pts(An(i).idx).xcoord
    
    If IsDlinaUkl Then
        p(0) = xcoord: p(1) = UTable(Umode, 8): p(2) = 0#
        pp(0) = xcoord: pp(1) = p(1) - UTable(Umode, 9): pp(2) = 0#
        Set Line = DS.AddLine(p, pp)
        ' уклон и растояние слева от точки format mid
        If An(i).uklon > 0 Then
            p(0) = 2 + xcoord - An(i).dist / Hscale: p(1) = UTable(Umode, 10): p(2) = 0
            ' уклоны 90 градусов не рисуем
            If An(i).uklon < 10000 Then
                Set txtObJ = PutTextPF(An(i).uklon * UTable(Umode, 14), UTable(Umode, 12), UTable(Umode, 2), p, acAlignmentLeft, 0)
            End If
            p(0) = xcoord - 2: p(1) = UTable(Umode, 11)
            ' нулевые расстояние не рисуем
            If An(i).dist <> 0 Then
                Set txtObJ = PutTextPF(An(i).dist, UTable(Umode, 4), UTable(Umode, 2), p, acAlignmentRight, 0)
            End If
            p(0) = xcoord: p(1) = UTable(Umode, 8): p(2) = 0#
            pp(0) = xcoord - An(i).dist / Hscale: pp(1) = p(1) - UTable(Umode, 9): pp(2) = 0#
        ElseIf An(i).uklon < 0 Then
            p(0) = xcoord - 2: p(1) = UTable(Umode, 10): p(2) = 0
            ' уклоны 90 градусов не рисуем
            If An(i).uklon > -10000 Then
                Set txtObJ = PutTextPF(An(i).uklon * (-1) * UTable(Umode, 14), UTable(Umode, 12), UTable(Umode, 2), p, acAlignmentRight, 0)
            End If
            p(0) = 2 + xcoord - An(i).dist / Hscale: p(1) = UTable(Umode, 11)
            ' нулевые расстояние не рисуем
            If An(i).dist <> 0 Then
                Set txtObJ = PutTextPF(An(i).dist, UTable(Umode, 4), UTable(Umode, 2), p, acAlignmentLeft, 0)
            End If
            p(0) = xcoord: p(1) = UTable(Umode, 8) - UTable(Umode, 9): p(2) = 0#
            pp(0) = xcoord - An(i).dist / Hscale: pp(1) = UTable(Umode, 8): pp(2) = 0#
        Else
            p(0) = xcoord - An(i).dist / Hscale / 2: p(1) = UTable(Umode, 10): p(2) = 0
            ' нулевые уклоны округляем до 1 знака
            Set txtObJ = PutTextPF(An(i).uklon, 1, UTable(Umode, 2), p, acAlignmentCenter, 0)
            p(1) = UTable(Umode, 11)
            ' нулевые расстояние не рисуем
            If An(i).dist <> 0 Then
                Set txtObJ = PutTextPF(An(i).dist, UTable(Umode, 4), UTable(Umode, 2), p, acAlignmentCenter, 0)
            End If
            p(0) = xcoord: p(1) = UTable(Umode, 8) - UTable(Umode, 9) / 2: p(2) = 0#
            pp(0) = xcoord - An(i).dist / Hscale: pp(1) = p(1): pp(2) = 0#
        End If
        Set Line = DS.AddLine(p, pp)
    End If
    
    If IsVinosk And UTable(Umode, 13) = 1 Then
        ' полка с росписью вертикального угла
        p(0) = xcoord: p(1) = p1(1): p(2) = 0
        pp(0) = p(0): pp(1) = p1(1) + 30: pp(2) = p(2)
        Set Line = DS.AddLine(p, pp)
        If An(i).biss < 0 Then
            CopyPt pp, p
            pp(0) = pp(0) + 20
        Else
            CopyPt p, pp
            pp(0) = pp(0) + 20
        End If
        Set Line = DS.AddLine(p, pp)
        p(0) = xcoord + 1.5: p(1) = p1(1) + 30 - 4: p(2) = 0
        Set txtObJ = PutText("Уг" + Trim(str(An(i).Ugol)) + "%%d" + format(An(i).minutes, "00") + "'", TextH, p, acAlignmentLeft, 0)
        p(1) = p(1) - 4.5
        Set txtObJ = PutText("R=" + Trim(str(An(i).Rad)) + "м", TextH, p, acAlignmentLeft, 0)
        p(1) = p(1) - 4.5
        Set txtObJ = PutTextP("T=" + format(An(i).tang, "0.00") + "м", TextH, p, acAlignmentLeft, 0)
        p(1) = p(1) - 4.5
        Set txtObJ = PutTextP("Б=" + format(An(i).biss, "0.00") + "м", TextH, p, acAlignmentLeft, 0)
        p(1) = p(1) - 4.5
        Set txtObJ = PutText("Вуг=" + Trim(str(pts(An(i).idx).pipe)), TextH, p, acAlignmentLeft, 0)
        p(1) = p(1) - 4.5
        Dim myStr As String
        myStr = MtoPK(An(i).DX * 100)
'        myStr = StrChg(Trim(format(An(i).DX, ".0000")), ",", "+")
'        myStr = Mid(myStr, 1, Len(myStr) - 1) + "." + Mid(myStr, Len(myStr))
        Set txtObJ = PutText(myStr, TextH, p, acAlignmentLeft, 0)
    End If
    
    ReDim Preserve points(i * 2 + 3)
'    points(i * 2 + 2) = xcoord: points(i * 2 + 3) = p2(1) + ((pts(An(i).idx).land - pts(An(i).idx).deep - pts(0).land) / Vscale)
    points(i * 2 + 2) = xcoord: points(i * 2 + 3) = p2(1) + ((pts(0).pipe - pts(0).land + pts(An(i).idx).pipe - pts(0).pipe) / Vscale)
Next i

' отрисовка трубы
Dim plineObj As AcadLWPolyline, plineObj2 As AcadLWPolyline

If IsLandLine Then
    Set plineObj = DS.AddLightWeightPolyline(lpoints)
End If

If IsTrubaLine Then
    Set plineObj = DS.AddLightWeightPolyline(points)
    plineObj.Lineweight = acLnWt050
    Set plineObj2 = plineObj.Copy
    p(0) = 0: p(1) = 0: p(2) = 0
    CopyPt p, pp
    If NizTrubi Then
        pp(1) = pp(1) + Dpipe / Vscale / 1000
    Else
        pp(1) = pp(1) - Dpipe / Vscale / 1000
    End If
    plineObj2.Move p, pp
End If

Set_Layer (oldLayer)
ThisDrawing.Regen acActiveViewport

End Sub

Sub MoveUG()
'перенос и разворот отметок углов вида +75.79 Уг пр.42°06'
'а также сдвиг вверх и удаление плюсовок всех остальных отметок
    Dim sset As AcadSelectionSet
    Dim FilterType(0) As Integer
    Dim FilterData(0) As Variant
    Dim l() As AcadEntity, num As Integer, p(2) As Double, numlen As Integer, i As Integer, txtObJ As AcadText
    Dim point1(0 To 2) As Double
    Dim point2(0 To 2) As Double
    point1(0) = 0: point1(1) = 0: point1(2) = 0
    point2(0) = 0: point2(1) = 35: point2(2) = 0
    
    num = CInt(InputBox("Введите номер первого угла"))
    ' выбор текста
    Set sset = GetSelSet("mdv")
    FilterType(0) = 0
    FilterData(0) = "text"
    sset.SelectOnScreen FilterType, FilterData
    numlen = sset.Count
    ReDim l(numlen)
    For i = 0 To numlen - 1
        Set l(i) = sset.Item(i)
    Next i
'    EntSortX L, NumLen
    For i = numlen - 1 To 0 Step -1
        If RegExp(l(i).TextString, "\+\d+[\.,]\d+ Уг", True) Then
            p(0) = EntGetX(l(i))
            p(1) = EntGetY(l(i)) - 100
            p(2) = 0
            Set txtObJ = PutText("Уг." + str(num), 2.5, p, acAlignmentCenter, 0)
            num = num + 1
            l(i).Delete
        Else
            If RegExp(l(i).TextString, "\+\d+[\.,]\d+", True) Then
                l(i).TextString = RegExpReplace(l(i).TextString, "\+\d+[\.,]\d+", "", , False)
            End If
            l(i).Move point1, point2
        End If
    Next i
    sset.Delete
End Sub

Attribute VB_Name = "Utils"
Option Explicit
Option Base 0

Sub SetFont_GOST()
'установить всему тексту фонт GOST_SNG
    Dim TextColl As AcadTextStyles
    Set TextColl = ThisDrawing.TextStyles
    
    Dim ts As AcadTextStyle
    Dim typeFace As String
    Dim Bold As Boolean
    Dim Italic As Boolean
    Dim charSet As Long
    Dim PitchandFamily As Long
    
    For Each ts In TextColl
        ts.GetFont typeFace, Bold, Italic, charSet, PitchandFamily
        ts.SetFont "GOST_SNG", Bold, Italic, charSet, PitchandFamily
    Next ts
    
    ThisDrawing.Regen acAllViewports

End Sub

Function PutTextPaper(txt As String, H As Double, p() As Double, align As Integer, angle As Double) As AcadText
Dim txtObJ As AcadText
    Set txtObJ = ThisDrawing.PaperSpace.AddText(txt, p, H)
    txtObJ.Alignment = align
    If align <> acAlignmentLeft Then
        txtObJ.TextAlignmentPoint = p
    End If
    If angle <> 0 Then txtObJ.Rotate p, Rad(angle)
    Set PutTextPaper = txtObJ
End Function

Function PutText(txt As String, H As Double, p() As Double, align As Integer, angle As Double) As AcadText
Dim txtObJ As AcadText
Dim DS As Object

If ThisDrawing.ActiveSpace = acModelSpace Then
    Set DS = ThisDrawing.ModelSpace
Else
    Set DS = ThisDrawing.PaperSpace
End If
    
    If txt = "" Then txt = "___"
    Set txtObJ = DS.AddText(txt, p, H)
    txtObJ.Alignment = align
    If align <> acAlignmentLeft Then
        txtObJ.TextAlignmentPoint = p
    End If
    If angle <> 0 Then txtObJ.Rotate p, Rad(angle)
    Set PutText = txtObJ
End Function

Function PutTextP(txt As String, H As Double, p() As Double, align As Integer, angle As Double) As AcadText
Dim txtObJ As AcadText
Dim DS As Object

If ThisDrawing.ActiveSpace = acModelSpace Then
    Set DS = ThisDrawing.ModelSpace
Else
    Set DS = ThisDrawing.PaperSpace
End If
    Set txtObJ = DS.AddText(StrChg(txt, ",", "."), p, H)
    txtObJ.Alignment = align
    If align <> acAlignmentLeft Then
        txtObJ.TextAlignmentPoint = p
    End If
    If angle <> 0 Then txtObJ.Rotate p, Rad(angle)
    Set PutTextP = txtObJ
End Function

Function PutTextPF(txt As Double, perc As Double, H As Double, p() As Double, align As Integer, angle As Double) As AcadText
Dim txtObJ As AcadText, formstr As String, s As String, i As Integer, pp As Integer
Dim DS As Object

If ThisDrawing.ActiveSpace = acModelSpace Then
    Set DS = ThisDrawing.ModelSpace
Else
    Set DS = ThisDrawing.PaperSpace
End If
    
    pp = perc
    If pp = 0 Then
        s = Trim(str(txt))
    Else
        formstr = "0."
        For i = 1 To pp
            formstr = formstr + "0"
        Next i
        s = format(txt, formstr)
    End If
    Set txtObJ = DS.AddText(s, p, H)
    txtObJ.Alignment = align
    If align <> acAlignmentLeft Then
        txtObJ.TextAlignmentPoint = p
    End If
    If angle <> 0 Then txtObJ.Rotate p, Rad(angle)
    Set PutTextPF = txtObJ
End Function

Sub Set_Layer(LayName As String)
' Установить активный слой, если слоя с таким именем нету, то он создается
    Dim newLayer As AcadLayer, i As Integer
    
    For i = 0 To ThisDrawing.Layers.Count - 1
        If ThisDrawing.Layers.Item(i).Name = LayName Then
            ThisDrawing.ActiveLayer = ThisDrawing.Layers.Item(i)
            Exit Sub
        End If
    Next
     
    ' Create a Layer and make it the active layer
    Set newLayer = ThisDrawing.Layers.Add(LayName)
    ThisDrawing.ActiveLayer = newLayer
End Sub

Sub MDVGetPoint(ByRef pt() As Double, text As String)
    Dim varRet As Variant
    varRet = ThisDrawing.Utility.GetPoint(, text)
    pt(0) = varRet(0)
    pt(1) = varRet(1)
    pt(2) = varRet(2)
End Sub

Sub MDVGetPointDir(ByRef pt() As Double, oldpt() As Double, text As String)
    Dim varRet As Variant
    varRet = ThisDrawing.Utility.GetPoint(oldpt, text)
    pt(0) = varRet(0)
    pt(1) = varRet(1)
    pt(2) = varRet(2)
End Sub

Sub TestGetPoint()
    Dim varRet As Variant
    varRet = ThisDrawing.Utility.GetPoint(, "text")
    MsgBox str(varRet(0)) + " " + str(varRet(1)) + " " + str(varRet(2))
End Sub

Sub CopyPt(from() As Double, ByRef into() As Double)
    into(0) = from(0)
    into(1) = from(1)
    into(2) = from(2)
End Sub

Sub CopyPtPlus(from() As Double, ByRef into() As Double, DX As Double, dy As Double, dz As Double)
    into(0) = from(0) + DX
    into(1) = from(1) + dy
    into(2) = from(2) + dz
End Sub

Function GetSelSet(sname As String) As AcadSelectionSet
' Возвращает именованый SelectionSet если его нет то предварительно создает
    Dim sset As AcadSelectionSet, exist As Boolean
    exist = False
    For Each sset In ThisDrawing.SelectionSets
        If sset.Name = sname Then
            sset.Clear
            exist = True
            Exit For
        End If
    Next sset
    If Not exist Then Set sset = ThisDrawing.SelectionSets.Add(sname)
    Set GetSelSet = sset
End Function

Sub DimSumm()
' Выводит информацию о сумме линейных размеров - реальной и исправленной
    Dim sset As AcadSelectionSet
    Set sset = GetSelSet("mdv")
    Dim FilterType(0) As Integer
    Dim FilterData(0) As Variant
    FilterType(0) = 0
    FilterData(0) = "dimension"
    sset.SelectOnScreen FilterType, FilterData
    Dim entry As AcadEntity, sum As Double, sumover As Double
    For Each entry In sset
        ' hack for recalc real lenght
        entry.TextOverride = entry.TextOverride
        sum = sum + entry.Measurement
        If entry.TextOverride = "" Or entry.TextOverride = "<>" Then
            sumover = sumover + entry.Measurement
        Else
            sumover = sumover + CDbl(entry.TextOverride)
        End If
    Next entry
    sset.Delete
    MsgBox "Реальная сумма размеров=" + format(sum) + Chr(10) + Chr(13) + _
        "Виртуальная сумма=" + format(sumover), vbInformation, MsgTitle
End Sub

Sub Excavation()
'Расчет разработки траншеи, разбитой по глубинам
    Dim sset As AcadSelectionSet, sset2 As AcadSelectionSet
    Dim FilterType(0) As Integer
    Dim FilterData(0) As Variant
    Dim nl As String, numlen As Integer, NumH As Integer
    Dim l() As AcadEntity
    Dim H() As AcadEntity
    Dim i As Integer, so As String, sum As Double
    Dim dlini(0 To 100) As Double, Hsr_Idx As Integer
    Dim WAppObj As Word.Application, Page As Variant
    
    nl = Chr(13) & Chr(10)
    Set sset = GetSelSet("mdv")
    FilterType(0) = 0
    FilterData(0) = "text"
    ' выбор расстояний
    sset.SelectOnScreen FilterType, FilterData
    Set sset2 = GetSelSet("mdv2")
    ' выбор глубин
    sset2.SelectOnScreen FilterType, FilterData

    numlen = sset.Count
    NumH = sset2.Count
    If numlen + 1 <> NumH Then
        MsgBox "Не совпадает количество расстояний и глубин траншеи", vbExclamation, MsgTitle
        GoTo err
    End If
    
    ReDim l(numlen)
    ReDim H(NumH)
    
    For i = 0 To numlen - 1
        Set l(i) = sset.Item(i)
    Next i
    For i = 0 To NumH - 1
        Set H(i) = sset2.Item(i)
    Next i
    
    EntSortX l, numlen
    EntSortX H, NumH
    
    For i = 0 To numlen - 1
'расчет траншеи
        Hsr_Idx = Round((EntD(H(i)) + EntD(H(i + 1))) / 2, 1) * 10
        dlini(Hsr_Idx) = dlini(Hsr_Idx) + EntD(l(i))
    Next i
    
    Set WAppObj = Word.Application
    Set Page = WAppObj.ActiveDocument
    For i = 0 To 100
        If dlini(i) <> 0 Then
            Selection.MoveRight Unit:=wdCell
            Selection.TypeText text:="-" + str(i / 10) + "м"
            Selection.MoveRight Unit:=wdCell
            Selection.TypeText text:="м"
            Selection.MoveRight Unit:=wdCell
            Selection.MoveRight Unit:=wdCell
            Selection.MoveRight Unit:=wdCell
            Selection.TypeText text:=str(dlini(i))
            Selection.MoveRight Unit:=wdCell
'            so = so + str(i / 10) + ": " + str(dlini(i)) + "м" + nl
'            sum = sum + dlini(i)
        End If
    Next i
'    so = so + "Итого: " + str(sum) + "м"
    
'    MsgBox so, , MsgTitle
    
err:
    sset.Delete
    sset2.Delete
End Sub

Sub DeepVolume()
' Расчет объема траншеи с откосами по формуле Винклера
' Vтр = ((F1+F2)/2 - (m*(H1+H2)^2)/6)*L
' F1, F2 - площади крайних сечений траншеи
' m - к-т крутизны откоса, опред. в зависимости от типа грунта
' H1, H2 - глубина траншеи в двух крайних поперечных сечениях
' также подсчитать валик(если он есть)
'10.10.2013 f дополнен вывод о несовпадении глубин и расстояний
    Dim sset As AcadSelectionSet, sset2 As AcadSelectionSet
    Dim FilterType(0) As Integer
    Dim FilterData(0) As Variant
    Dim l() As AcadEntity
    Dim H() As AcadEntity
    Dim i As Integer
    Dim v As Double, F1 As Double, F2 As Double, m As Double, Btr As Double
    Dim Ltras As Double, numlen As Integer, NumH As Integer
    Dim li As Double, hi As Double, hi1 As Double
    Dim nl As String, Hsr As Double, MinH As Double
    Dim Vval As Double, Bval As Double, mval As Double, Hval As Double
    
    DlgTran.Show
    If DlgTran.TextBox1.value = "" Or DlgTran.TextBox2.value = "" Then
        MsgBox "Неверные исходные данные", vbCritical, MsgTitle
        Exit Sub
    End If
On Error GoTo err:
    Btr = CDbl(StrChg(DlgTran.TextBox1.value, ".", ","))
    m = CDbl(StrChg(DlgTran.TextBox2.value, ".", ","))
    MinH = CDbl(StrChg(DlgTran.TextBox3.value, ".", ","))
    Bval = CDbl(StrChg(DlgTran.TextBox4.value, ".", ","))
    mval = CDbl(StrChg(DlgTran.TextBox5.value, ".", ","))
    nl = Chr(13) & Chr(10)
    Set sset = GetSelSet("mdv")
    FilterType(0) = 0
    FilterData(0) = "text"
    ' выбор расстояний
    sset.SelectOnScreen FilterType, FilterData
    Set sset2 = GetSelSet("mdv2")
    ' выбор глубин
    sset2.SelectOnScreen FilterType, FilterData
    
    numlen = sset.Count
    NumH = sset2.Count
    If numlen + 1 <> NumH Then
        MsgBox "Не совпадает количество расстояний (" + str(numlen) + ") и глубин траншеи (" + str(NumH) + "). Внимание: глубин должно быть на 1 больше чем расстояний.", vbExclamation, MsgTitle
        GoTo err
    End If
    
    ReDim l(numlen)
    ReDim H(NumH)
    
    For i = 0 To numlen - 1
        Set l(i) = sset.Item(i)
    Next i
    For i = 0 To NumH - 1
        Set H(i) = sset2.Item(i)
    Next i
    
    EntSortX l, numlen
    EntSortX H, NumH
    
    v = 0: Ltras = 0: Hsr = 0
    For i = 0 To numlen - 1
'расчет траншеи
        li = EntD(l(i)): hi = EntD(H(i)): hi1 = EntD(H(i + 1))
        F1 = (Btr + m * hi) * hi
        F2 = (Btr + m * hi1) * hi1
        v = v + ((F1 + F2) / 2 - (m * (hi + hi1) ^ 2) / 6) * li
        Ltras = Ltras + li
        Hsr = Hsr + li * (hi + hi1) / 2
'расчет валика
        hi = MinH - hi: If hi < 0 Then hi = 0
        hi1 = MinH - hi1: If hi1 < 0 Then hi1 = 0
        F1 = (Bval + mval * hi) * hi
        F2 = (Bval + mval * hi1) * hi1
        Vval = Vval + ((F1 + F2) / 2 - (mval * (hi + hi1) ^ 2) / 6) * li
        Hval = Hval + li * (hi + hi1) / 2
    Next i
    
    MsgBox "Объем траншеи на участке = " & format(v, "0.000") & " м3" & nl & _
        "Средняя глубина траншеи на участке = " & format(Hsr / Ltras, "0.000") & " м" & nl & _
        "Длина участка = " & Ltras & " м" & nl & _
        "Объем валика = " & format(Vval, "0.000") & " м3" & nl & _
        "Средняя высота валика на участке = " & format(Hval / Ltras, "0.000") & " м", , MsgTitle
err:
    sset.Delete
    sset2.Delete
End Sub

Function EntD(ByVal a As AcadEntity) As Double
    EntD = CDbl(StrChg(a.TextString, ".", ","))
End Function

Sub SOtoWord()
    Dim sset As AcadSelectionSet, sset2 As AcadSelectionSet
    Dim FilterType(0) As Integer
    Dim FilterData(0) As Variant
    Dim l() As AcadEntity
    Dim H() As AcadEntity
    Dim i As Integer
    Dim v As Double, F1 As Double, F2 As Double, m As Double, Btr As Double
    Dim Ltras As Double, numlen As Integer, NumH As Integer
    Dim li As Double, hi As Double, hi1 As Double
    Dim nl As String, Hsr As Double
    Dim WAppObj As Word.Application, Page As Variant

    
    ' выбор текста
    Set sset = GetSelSet("mdv")
    FilterType(0) = 0
    FilterData(0) = "text"
    sset.SelectOnScreen FilterType, FilterData
    numlen = sset.Count
    ReDim l(numlen)
    For i = 0 To numlen - 1
        Set l(i) = sset.Item(i)
    Next i
    EntSortY l, numlen
    Set WAppObj = Word.Application
    Set Page = WAppObj.ActiveDocument
    For i = numlen - 1 To 0 Step -1
        Selection.TypeText text:=l(i).TextString
        Selection.MoveRight Unit:=wdCell
        Selection.MoveRight Unit:=wdCell
        Selection.MoveRight Unit:=wdCell
        Selection.MoveRight Unit:=wdCell
        Selection.MoveRight Unit:=wdCell
        Selection.MoveRight Unit:=wdCell
        Selection.MoveRight Unit:=wdCell
        Selection.MoveRight Unit:=wdCell
        Selection.MoveRight Unit:=wdCell
    Next i
    sset.Delete
End Sub

Sub AddTextEnd()
    Dim sset As AcadSelectionSet
    Dim FilterType(0) As Integer
    Dim FilterData(0) As Variant
    Dim l() As AcadEntity
    Dim ch As String
    Dim i As Integer, numlen As Integer
    ch = InputBox("Введите строку для добавления в конец", , "*")
    ' выбор текста
    Set sset = GetSelSet("mdv")
    FilterType(0) = 0
    FilterData(0) = "text"
    sset.SelectOnScreen FilterType, FilterData
    numlen = sset.Count
    ReDim l(numlen)
    For i = 0 To numlen - 1
        Set l(i) = sset.Item(i)
        l(i).TextString = l(i).TextString + ch
    Next i
    sset.Delete
End Sub

Sub UklonToWord()
    Static initpk As Double
    Dim sset As AcadSelectionSet
    Dim FilterType(0) As Integer
    Dim FilterData(0) As Variant
    Dim l() As AcadEntity
    Dim i As Integer, numlen As Integer
    Dim WAppObj As Word.Application, Page As Variant
    Dim pk1 As Double, sum As Double, dlina As Double, uklon As Double, oldukl As Double, gr As Double
    
    StrToDouble InputBox("Введите значения начального пикета трассы (пример: ПК1+50 вводить как 1,50)", , format(initpk)), pk1
    pk1 = pk1 * 100
    sum = 0
    oldukl = 1000
    
    ' выбор текста
    Set sset = GetSelSet("mdv")
    FilterType(0) = 0
    FilterData(0) = "text"
    sset.SelectOnScreen FilterType, FilterData
    numlen = sset.Count
    ReDim l(numlen)
    For i = 0 To numlen - 1
        Set l(i) = sset.Item(i)
    Next i
    EntSortX l, numlen
    Set WAppObj = Word.Application
    Set Page = WAppObj.ActiveDocument
    i = 0
    While i < numlen
        If EntGetY(l(i)) > EntGetY(l(i + 1)) Then
            StrToDouble l(i).TextString, uklon
            StrToDouble l(i + 1).TextString, dlina
        Else
            StrToDouble l(i + 1).TextString, uklon
            uklon = uklon * (-1)
            StrToDouble l(i).TextString, dlina
        End If
        Selection.TypeText text:=MtoPK(pk1 + sum) + " - " + MtoPK(pk1 + sum + dlina)
        sum = sum + dlina
        Selection.MoveRight Unit:=wdCell
        If oldukl = 1000 Then
            Selection.TypeText text:="н/д"
        Else
            gr = Abs(Gradus(Atn(oldukl - uklon)))
            Selection.TypeText text:=format(Int(gr))
            Selection.InsertSymbol Font:="GOST_SNG", CharacterNumber:=176, Unicode:=True
            Selection.TypeText text:=format((gr - Int(gr)) * 60, "0") + "'"
        End If
        oldukl = uklon
        Selection.MoveRight Unit:=wdCell
        Selection.TypeText text:=format(dlina, "0.0")
        Selection.MoveRight Unit:=wdCell
        Selection.TypeText text:=format(uklon, "0.0000")
        Selection.MoveRight Unit:=wdCell
        Selection.TypeText text:=format(uklon * dlina, "0.00")
        Selection.MoveRight Unit:=wdCell
        i = i + 2
    Wend
    sset.Delete
    initpk = (pk1 + sum) / 100
End Sub

Sub UgPovToWord()
    Dim sset As AcadSelectionSet
    Dim FilterType(0) As Integer
    Dim FilterData(0) As Variant
    Dim l() As AcadEntity
    Dim i As Integer, numlen As Integer, BaseX As Double, Tabs(100, 9) As String
    Dim MAXROW As Integer, row As Integer, col As Integer, Base(0 To 2) As Double
    Dim WAppObj As Word.Application, Page As Variant
    Const DeltaX = 20, DeltaY = 8
    Dim y As Double, X As Double, j As Integer, s As String
    
    MAXROW = 0
    ' выбор текста
    MDVGetPoint Base, "Укажите левую верхнюю точку данных таблицы"
    Set sset = GetSelSet("mdv")
    FilterType(0) = 0
    FilterData(0) = "text"
    sset.SelectOnScreen FilterType, FilterData
    numlen = sset.Count
    ReDim l(numlen)
    For i = 0 To numlen - 1
        Set l(i) = sset.Item(i)
    Next i
    EntSortY l, numlen
    Set WAppObj = Word.Application
    Set Page = WAppObj.ActiveDocument
'распихиваем тексты по ячейкам таблицы
    For i = numlen - 1 To 0 Step -1
        y = EntGetY(l(i))
        X = EntGetX(l(i))
        s = RegExpReplace(l(i).TextString, "%%d", Chr(176), True)
        col = Int((X - Base(0)) / DeltaX)
        If col = 2 Then
            row = Int((Base(1) - y + 4) / DeltaY)
        Else
            row = Int((Base(1) - y) / DeltaY)
        End If
        If Tabs(row, col) <> "" Then
            Tabs(row, col) = Tabs(row, col) + Chr(11) + s
        Else
            Tabs(row, col) = s
        End If
        If MAXROW < row Then MAXROW = row
    Next i

'выводим табличку в ворд
    For i = 0 To MAXROW
        For j = 0 To 8
            If Tabs(i, j) <> "" Then
                Selection.TypeText text:=Tabs(i, j)
            End If
            Selection.MoveRight Unit:=wdCell
        Next j
    Next i
    sset.Delete
    
End Sub

Sub UgPovToWord2()
    Dim sset As AcadSelectionSet
    Dim FilterType(0) As Integer
    Dim FilterData(0) As Variant
    Dim l() As AcadEntity
    Dim i As Integer, numlen As Integer, BaseX As Double, Tabs(100, 9) As String
    Dim MAXROW As Integer, row As Integer, col As Integer, Base(0 To 2) As Double
    Dim WAppObj As Word.Application, Page As Variant
    Const DeltaX = 20, DeltaY = 8
    Dim y As Double, X As Double, j As Integer, s As String
    
    MAXROW = 0
    ' выбор текста
    Set sset = GetSelSet("mdv")
    FilterType(0) = 0
    FilterData(0) = "text"
    sset.SelectOnScreen FilterType, FilterData
    numlen = sset.Count
    ReDim l(numlen)
'Фильтруем и сортируем
    For i = 0 To numlen - 1
        If RegExp(sset.Item(i).TextString, "\+\d{1,2}\.\d.+УГ\d", True) Then
            MsgBox sset.Item(i).TextString
            Set l(i) = sset.Item(i)
        End If
    Next i
Exit Sub
    numlen = i
    EntSortX l, numlen
    Set WAppObj = Word.Application
    Set Page = WAppObj.ActiveDocument
'распихиваем тексты по ячейкам таблицы
    For i = numlen - 1 To 0 Step -1
        y = EntGetY(l(i))
        X = EntGetX(l(i))
        s = RegExpReplace(l(i).TextString, "%%d", Chr(176), True)
        col = Int((X - Base(0)) / DeltaX)
        If col = 2 Then
            row = Int((Base(1) - y + 4) / DeltaY)
        Else
            row = Int((Base(1) - y) / DeltaY)
        End If
        If Tabs(row, col) <> "" Then
            Tabs(row, col) = Tabs(row, col) + Chr(11) + s
        Else
            Tabs(row, col) = s
        End If
        If MAXROW < row Then MAXROW = row
    Next i

'выводим табличку в ворд
    For i = 0 To MAXROW
        For j = 0 To 8
            If Tabs(i, j) <> "" Then
                Selection.TypeText text:=Tabs(i, j)
            End If
            Selection.MoveRight Unit:=wdCell
        Next j
    Next i
    sset.Delete
End Sub

Sub findblock()
    Dim sset As AcadSelectionSet
    Dim FilterType(0) As Integer
    Dim FilterData(0) As Variant
    Dim s As AcadEntity
    Set sset = GetSelSet("mdv")
    FilterType(0) = 2
    FilterData(0) = "www"
    sset.Select acSelectionSetAll, , , FilterType, FilterData
    For Each s In sset
        s.Explode
        s.Delete
    Next s
End Sub

Sub SavaAndCloseAll()
Dim doc As AcadDocument
For Each doc In Documents
        doc.Save
        doc.Close
    Next
End Sub

Sub AllDocsTextChange()
' Изменить текст во всех открытых документах. Поддерживает регекспы
Dim s1 As String, s2 As String, doc As AcadDocument
    s1 = "^Н. контр$"     'что ищем
    s2 = "Н. контр."       'на что меняем
    For Each doc In Documents
        doc.Activate
'                                                                              findblock        'убрать нахуй. потом
        TextChangeG s1, s2
        doc.Save
    Next
End Sub

Sub NumerateListFromFileName()
    Dim sset As AcadSelectionSet, doc As AcadDocument
    Dim FilterType(0) As Integer
    Dim FilterData(0) As Variant
    Dim s As AcadEntity, at As Variant
    Dim i As Integer, j As Integer, num As String
    For Each doc In Documents
        doc.Activate
        i = InStr(doc.Name, "стр.")
        j = InStr(doc.Name, ".dwg")
        num = Mid(doc.Name, i + 4, j - (i + 4))
        Set sset = GetSelSet("mdv")
        FilterType(0) = 2
        FilterData(0) = "Рамка 10х7 со звездой"
        sset.Select acSelectionSetAll, , , FilterType, FilterData
        For Each s In sset
            at = s.GetAttributes()
            at(0).TextString = num
        Next s
        doc.Save
    Next
End Sub

Sub TextGenerator()
'19.09.2013 Генерирует тексотую строку по заданному шаблону в указанных точках
'20.09.2013 - добавил получение уцс и поворот на ее матрицу - все равно не то
    Dim s As AcadEntity, i As Integer
    Dim prefix As String, postfix As String
    Dim t As AcadText
    Dim sp(0 To 2) As Double, H As Double, currUcs As AcadUCS
    Dim TransMatrix As Variant
    
    prefix = InputBox("Префикс")
    i = CInt(InputBox("Начальное значение"))
    postfix = InputBox("Постфикс")
    H = CDbl(InputBox("Высота текста"))
    ' Get the current saved UCS of the active document. If the current UCS is
    ' not saved, then add a new UCS to the UserCoordinateSystems collection
    If ThisDrawing.GetVariable("UCSNAME") = "" Then
        ' Current UCS is not saved so get the data and save it
        With ThisDrawing
            Set currUcs = .UserCoordinateSystems.Add( _
                            .GetVariable("UCSORG"), _
                            .Utility.TranslateCoordinates(.GetVariable("UCSXDIR"), acUCS, acWorld, 0), _
                            .Utility.TranslateCoordinates(.GetVariable("UCSYDIR"), acUCS, acWorld, 0), _
                            "OriginalUCS")
        End With
    Else
        Set currUcs = ThisDrawing.ActiveUCS  'current UCS is saved
    End If
    TransMatrix = currUcs.GetUCSMatrix()
    On Error GoTo endsub
    While True
        MDVGetPoint sp, "Точка вставки"
        Set t = PutText(prefix + format(i) + postfix, H, sp, acAlignmentLeft, 0)
        TransMatrix(0, 3) = 0
        TransMatrix(1, 3) = 0
        TransMatrix(2, 3) = 0
        t.TransformBy (TransMatrix)
        t.Update
        i = i + 1
    Wend
endsub:
End Sub

Sub testTextGenerator()
'19.09.2013 Генерирует тексотую строку по заданному шаблону в указанных точках
'20.09.2013 - добавил получение уцс и поворот на ее матрицу - все равно не то
    Dim s As AcadEntity, i As Integer
    Dim prefix As String, postfix As String
    Dim t As AcadText
    Dim sp(0 To 2) As Double, H As Double, currUcs As AcadUCS
    Dim TransMatrix As Variant
    
    prefix = "pref"
    i = 1
    postfix = ""
    H = 5
    ' Get the current saved UCS of the active document. If the current UCS is
    ' not saved, then add a new UCS to the UserCoordinateSystems collection
    If ThisDrawing.GetVariable("UCSNAME") = "" Then
        ' Current UCS is not saved so get the data and save it
        With ThisDrawing
            Set currUcs = .UserCoordinateSystems.Add( _
                            .GetVariable("UCSORG"), _
                            .Utility.TranslateCoordinates(.GetVariable("UCSXDIR"), acUCS, acWorld, 0), _
                            .Utility.TranslateCoordinates(.GetVariable("UCSYDIR"), acUCS, acWorld, 0), _
                            "OriginalUCS")
        End With
    Else
        Set currUcs = ThisDrawing.ActiveUCS  'current UCS is saved
    End If
    TransMatrix = currUcs.GetUCSMatrix()
    On Error GoTo endsub
    While True
        MDVGetPoint sp, "Точка вставки"
        Set t = PutText(prefix + format(i) + postfix, H, sp, acAlignmentLeft, 0)
        t.TransformBy (TransMatrix)
        t.Update
        i = i + 1
    Wend
endsub:
End Sub

Sub TextNumeratePrefix()
'19.09.2013 пронумеровать последовательно текстовые отметки по одной, с префиксом и/или постфиксом (опционально)
    Dim sset As AcadSelectionSet
    Dim FilterType(0) As Integer
    Dim FilterData(0) As Variant
    Dim s As AcadEntity, i As Integer
    Dim prefix As String, postfix As String
    Set sset = GetSelSet("mdv")
    FilterType(0) = 0
    FilterData(0) = "text"
    prefix = InputBox("Префикс")
    i = CInt(InputBox("Начальное значение"))
    postfix = InputBox("Постфикс")
    While True
        sset.SelectOnScreen FilterType, FilterData
        If sset.Count < 1 Then
            sset.Delete
            End
        End If
        sset.Item(0).TextString = prefix + format(i) + postfix
        i = i + 1
        sset.Clear
    Wend
End Sub

Sub TextAverage()
'03.12.2013 - вычисляет среднее значение из выбранных текстовых отметок
    Dim sset As AcadSelectionSet
    Dim s As AcadEntity, i As Double, sum As Double, d As Double
    
    Set sset = GetTextOnScreen
    i = 0
    sum = 0
    For Each s In sset
        If StrToDouble(s.TextString, d) = True Then
            sum = sum + d
            i = i + 1
        End If
    Next s
    sset.Delete
    MsgBox "Среднее значение: " + format(sum / i, "0.00"), vbOKOnly
End Sub

Sub TextChangeMul()
'23.09.2013 - изменят числовой текст умножая его содержимое на коэффициент
    Dim sset As AcadSelectionSet
    Dim s As AcadEntity, i As Double, d As Double, z As Integer, form_str As String, k As Integer
    
    StrToDouble InputBox("Коэффициент изменения"), i
    z = CInt(InputBox("Точность (число знаков после запятой)"))
    form_str = "0."
    For k = 1 To z
        form_str = form_str + "0"
    Next k
    Set sset = GetTextOnScreen
    For Each s In sset
        If StrToDouble(s.TextString, d) = True Then
            s.TextString = format(d * i, form_str)
        End If
    Next s
    sset.Delete
End Sub

Sub CalcDlinaLinii()
'26.09.2013 Расчитывает колонку "Длина линии" используя данные из колонки "Номер угла, пикет"
    Dim sset As AcadSelectionSet, entA() As AcadEntity, entB() As AcadEntity
    Dim i As Integer, j As Integer
    Dim k1 As String, k2 As String, d1 As Double, d2 As Double
    Dim s As AcadEntity
    
    Set sset = GetTextOnScreen
    ReDim entA(sset.Count / 2)
    i = 0
    For Each s In sset
        If RegExp(s.TextString, "ПК", True) Then
            Set entA(i) = s
            i = i + 1
        End If
    Next s
    EntSortY entA, i
    sset.Clear
    
    Set sset = GetTextOnScreen
    ReDim entB(sset.Count)
    i = 0
    For Each s In sset
        Set entB(i) = s
        i = i + 1
    Next s
    sset.Clear
    EntSortY entB, i
    
    For j = 0 To i - 1
        k1 = entA(j).TextString
        k1 = RegExpReplace(k1, "ПК", "", True)
        k1 = RegExpReplace(k1, "\+", "", True)
        StrToDouble k1, d1
        k2 = entA(j + 1).TextString
        k2 = RegExpReplace(k2, "ПК", "", True)
        k2 = RegExpReplace(k2, "\+", "", True)
        StrToDouble k2, d2
        entB(j).TextString = format(d1 - d2, "0.00")
    Next j
    sset.Delete
End Sub

Function GetTextOnScreen() As AcadSelectionSet
'23.09.2013 - Возвращает выбранные на экране текстовые объекты
    Dim sset As AcadSelectionSet
    Dim FilterType(0) As Integer
    Dim FilterData(0) As Variant
    
    FilterType(0) = 0
    FilterData(0) = "text"
    Set sset = GetSelSet("mdv1")
    sset.SelectOnScreen FilterType, FilterData
    Set GetTextOnScreen = sset
End Function

Sub TextChangeG(sfrom As String, sto As String)
    Dim sset As AcadSelectionSet
    Dim FilterType(0) As Integer
    Dim FilterData(0) As Variant
    Dim s As AcadEntity
    Set sset = GetSelSet("mdv")
    FilterType(0) = 0
    FilterData(0) = "text"
    sset.Select acSelectionSetAll, , , FilterType, FilterData
    For Each s In sset
        s.TextString = RegExpReplace(s.TextString, sfrom, sto, True)
    Next s
End Sub

Sub VRtoWord()
    Dim sset As AcadSelectionSet, sset2 As AcadSelectionSet
    Dim FilterType(0) As Integer
    Dim FilterData(0) As Variant
    Dim l() As AcadEntity
    Dim H() As AcadEntity
    Dim i As Integer
    Dim v As Double, F1 As Double, F2 As Double, m As Double, Btr As Double
    Dim Ltras As Double, numlen As Integer, NumH As Integer
    Dim li As Double, hi As Double, hi1 As Double
    Dim nl As String, Hsr As Double
    Dim WAppObj As Word.Application, Page As Variant

    ' выбор текста
    Set sset = GetSelSet("mdv")
    FilterType(0) = 0
    FilterData(0) = "text"
    sset.SelectOnScreen FilterType, FilterData
    numlen = sset.Count
    ReDim l(numlen)
    For i = 0 To numlen - 1
        Set l(i) = sset.Item(i)
    Next i
    EntSortY l, numlen
    Set WAppObj = Word.Application
    Set Page = WAppObj.ActiveDocument
    For i = numlen - 1 To 0 Step -1
        Selection.TypeText text:=l(i).TextString
        Selection.MoveRight Unit:=wdCell
        Selection.MoveRight Unit:=wdCell
        Selection.MoveRight Unit:=wdCell
        Selection.MoveRight Unit:=wdCell
        Selection.MoveRight Unit:=wdCell
        Selection.MoveRight Unit:=wdCell
    Next i
    sset.Delete
End Sub

Sub FixB()
'Уточнение верха трубы и глубины траншеи с учетом биссектрисы
    Static d As Double
    Dim Object As Object, b As Double, pos As Integer, s As String, l As Double, t As Double, DX As Double
        
    d = GetTextDefault(str(d), "Диаметр трубы, мм: ")
    GetTextObj "Выберите биссектрису: ", Object
    s = Object.TextString
    pos = InStr(1, s, "Б=", vbTextCompare)
    If pos <> 1 Then
        MsgBox "Это не биссектриса", vbExclamation
        Exit Sub
    End If
    StrToDouble Mid(s, 3, Len(s) - 3), b
    
    GetTextObj "Выберите отметку земли: ", Object
    StrToDouble Object.TextString, l
    
    GetTextObj "Выберите верх трубы: ", Object
    StrToDouble Object.TextString, t
    Object.TextString = format(Round(t + b, 2), "0.00")
    
    GetTextObj "Выберите глубину траншеи: ", Object
    StrToDouble Object.TextString, DX
    Object.TextString = format(Round(l - t - b + d / 1000, 2), "0.00")
End Sub

Sub GetTextObj(msg As String, ByRef obj As Object)
    Dim PickedPoint As Variant, TransMatrix As Variant, ContextData As Variant
    
    If msg <> "" Then
        ThisDrawing.Utility.prompt msg
    End If
    
    On Error Resume Next
    
    Do
        ThisDrawing.Utility.GetSubEntity obj, PickedPoint, TransMatrix, ContextData
    Loop Until TypeName(obj) = "IAcadText"
End Sub

Sub EntSortY(ByRef a() As AcadEntity, n As Integer)
'Сортировка по возрастанию энтов методом пузырька по оси Y
' Энты должны поодерживать свойство - insrtionpoint
    Dim i As Integer
    Dim isTurn As Boolean
    Dim ent As AcadEntity
    Do
        isTurn = False
        For i = 0 To n - 2
            If EntGetY(a(i)) > EntGetY(a(i + 1)) Then
                isTurn = True
                Set ent = a(i)
                Set a(i) = a(i + 1)
                Set a(i + 1) = ent
            End If
        Next i
    Loop While isTurn
End Sub

Function EntGetY(a As AcadEntity) As Double
'Возвращает самую верхнюю точку Энта AcadText
    Dim InsPoint As Variant
    InsPoint = a.InsertionPoint
    EntGetY = InsPoint(1)
End Function

Function EntYCompare(a As AcadEntity, b As AcadEntity) As Integer
'Сравнивает местоположение по оси Х два объекта, если "а" левее, то возвращает -1, если "а" правее
'возвращает 1, и если координата Х совпадает возвращает 0
    Dim minExt As Variant
    Dim maxExt As Variant
    Dim Xa As Double, Xb As Double, rez As Integer
    
    a.GetBoundingBox minExt, maxExt
    Xa = minExt(1)
    b.GetBoundingBox minExt, maxExt
    Xb = minExt(1)
    
    If Xa < Xb Then
        EntYCompare = -1
    ElseIf Xa > Xb Then
        EntYCompare = 1
    Else
        EntYCompare = 0
    End If

End Function


Sub EntSortX(ByRef a() As AcadEntity, n As Integer)
'Сортировка по возрастанию энтов методом пузырька по оси Х
' Энты должны поодерживать свойство - insrtionpoint
    Dim i As Integer
    Dim isTurn As Boolean
    Dim ent As AcadEntity
    Do
        isTurn = False
        For i = 0 To n - 2
            If EntGetX(a(i)) > EntGetX(a(i + 1)) Then
                isTurn = True
                Set ent = a(i)
                Set a(i) = a(i + 1)
                Set a(i + 1) = ent
            End If
        Next i
    Loop While isTurn
End Sub

Function EntGetX(a As AcadEntity) As Double
'Возвращает самую левую точку Энта AcadText
    Dim InsPoint As Variant
    InsPoint = a.InsertionPoint
    EntGetX = InsPoint(0)
End Function

Function EntXCompare(a As AcadEntity, b As AcadEntity) As Integer
'Сравнивает местоположение по оси Х два объекта, если "а" левее, то возвращает -1, если "а" правее
'возвращает 1, и если координата Х совпадает возвращает 0
    Dim minExt As Variant
    Dim maxExt As Variant
    Dim Xa As Double, Xb As Double, rez As Integer
    
    a.GetBoundingBox minExt, maxExt
    Xa = minExt(0)
    b.GetBoundingBox minExt, maxExt
    Xb = minExt(0)
    
    If Xa < Xb Then
        EntXCompare = -1
    ElseIf Xa > Xb Then
        EntXCompare = 1
    Else
        EntXCompare = 0
    End If

End Function

Sub TextSummToText()
    Dim sset As AcadSelectionSet
    Set sset = ThisDrawing.SelectionSets.Add("mdv0")
    Dim FilterType(0) As Integer
    Dim FilterData(0) As Variant
    FilterType(0) = 0
    FilterData(0) = "text"
    sset.SelectOnScreen FilterType, FilterData
    Dim entry As AcadEntity, sum As Double, sumover As Double, a As String
    For Each entry In sset
        a = StrChg(entry.TextString, ".", ",")
        sum = sum + CDbl(a)
    Next entry
    sset.Clear
    sset.SelectOnScreen FilterType, FilterData
    Set entry = sset.Item(0)
    entry.TextString = str(sum)
    sset.Delete
End Sub

Sub Change_Leader()
    Dim lmin As Integer, lmax As Integer, ldx As Integer
    lmin = CInt(InputBox("Введите минимальное значение выносок", , "1"))
    lmax = CInt(InputBox("Введите максимальное значение выносок", , "1000"))
    ldx = CInt(InputBox("Введите число на которое будет изменено значение выносок", , "1"))
    
    Dim sset As AcadSelectionSet
    Set sset = GetSelSet("mdv")
    Dim FilterType(0) As Integer
    Dim FilterData(0) As Variant
    FilterType(0) = 0
    FilterData(0) = "multileader"
    sset.Select acSelectionSetAll, , , FilterType, FilterData
    Dim entry As AcadEntity, a As AcadMText, ann As String, c As String, tag As Boolean, num As Integer, npos As Integer, i As Integer, kpos As Integer
    On Error Resume Next
    For Each entry In sset
'        If Not TypeName(entry.Annotation) = "Nothing" Then
        ann = entry.TextString
        num = 0
        npos = 100
' режим кривого отображения: "{\Fmonotxt.shx;54}"   \A1;33
            tag = False
            For i = 1 To Len(ann)
                c = Mid(ann, i, 1)
                If tag Then
                    ' skip a tag
                    If c = ";" Then tag = False
                ElseIf c = "\" And Mid(ann, i + 1, 1) = "F" Then
                    tag = True
                ElseIf c = "\" And Mid(ann, i + 1, 1) = "A" Then
                    tag = True
                ElseIf c = "0" Or c = "1" Or c = "2" Or c = "3" Or c = "4" Or c = "5" Or c = "6" Or c = "7" Or c = "8" Or c = "9" Then
                    If i < npos Then npos = i
                    kpos = i
                    num = num * 10 + CInt(c)
                End If
            Next i
            If num >= lmin And num <= lmax Then
                entry.TextString = Left(ann, npos - 1) + Trim(str(num + ldx)) + Mid(ann, kpos + 1)
            End If
'            MsgBox num
'        End If
        Next entry
    sset.Delete
    FilterData(0) = "leader"
    sset.Select acSelectionSetAll, , , FilterType, FilterData
    On Error Resume Next
    For Each entry In sset
'        If Not TypeName(entry.Annotation) = "Nothing" Then
        Set a = entry.Annotation
        ann = a.TextString
        num = 0
        npos = 100
' режим кривого отображения: "{\Fmonotxt.shx;54}"   \A1;33
            tag = False
            For i = 1 To Len(ann)
                c = Mid(ann, i, 1)
                If tag Then
                    ' skip a tag
                    If c = ";" Then tag = False
                ElseIf c = "\" And Mid(ann, i + 1, 1) = "F" Then
                    tag = True
                ElseIf c = "\" And Mid(ann, i + 1, 1) = "A" Then
                    tag = True
                ElseIf c = "0" Or c = "1" Or c = "2" Or c = "3" Or c = "4" Or c = "5" Or c = "6" Or c = "7" Or c = "8" Or c = "9" Then
                    If i < npos Then npos = i
                    kpos = i
                    num = num * 10 + CInt(c)
                End If
            Next i
            If num >= lmin And num <= lmax Then
                a.TextString = Left(ann, npos - 1) + Trim(str(num + ldx)) + Mid(ann, kpos + 1)
            End If
'            MsgBox num
'        End If
        Next entry
    sset.Delete
End Sub

Sub MarkLeaders()
Dim sset As AcadSelectionSet, it As AcadLeader
    Set sset = GetSelSet("mdv")
    Dim FilterType(0) As Integer
    Dim FilterData(0) As Variant
    FilterType(0) = 0
    FilterData(0) = "leader"
    sset.Select acSelectionSetAll, , , FilterType, FilterData
    Dim entry As AcadEntity, ess() As AcadEntity
    ReDim ess(sset.Count)
    Dim i As Integer, j As Integer
    i = 1
    For Each entry In sset
        Set ess(i) = entry
        i = i + 1
    Next entry
    sset.Delete
    For j = 1 To i - 1
        ess(j).DimensionLineColor = acGreen
    Next j
End Sub

Sub UnMarkLeaders()
Dim sset As AcadSelectionSet, it As AcadLeader
    Set sset = GetSelSet("mdv")
    Dim FilterType(0) As Integer
    Dim FilterData(0) As Variant
    FilterType(0) = 0
    FilterData(0) = "leader"
    sset.Select acSelectionSetAll, , , FilterType, FilterData
    Dim entry As AcadEntity, ess() As AcadEntity
    ReDim ess(sset.Count)
    Dim i As Integer, j As Integer
    i = 1
    For Each entry In sset
        Set ess(i) = entry
        i = i + 1
    Next entry
    sset.Delete
    For j = 1 To i - 1
        ess(j).DimensionLineColor = acRed
    Next j
End Sub

Sub DeleteText()
Dim sset As AcadSelectionSet
    Set sset = GetSelSet("mdv")
    Dim FilterType(0) As Integer
    Dim FilterData(0) As Variant
    FilterType(0) = 0
    FilterData(0) = "text"
    sset.SelectOnScreen FilterType, FilterData
    Dim entry As AcadEntity, ess() As AcadEntity
    ReDim ess(sset.Count)
    Dim i As Integer, j As Integer
    i = 1
    For Each entry In sset
        Set ess(i) = entry
        i = i + 1
    Next entry
    sset.Delete
    For j = 1 To i - 1
        ess(j).Delete
    Next j
End Sub

Sub TableReNum()
Dim t As AcadTable

End Sub
