(defun c:1 ()
(command "_view" "_r" "1")
)

(defun c:2 ()
(command "_view" "_r" "2")
)

(defun c:3 ()
(command "_view" "_r" "3")
)

(defun c:4 ()
(command "_view" "_r" "4")
)

(defun c:5 ()
(command "_view" "_r" "5")
)

(defun c:6 ()
(command "_view" "_r" "6")
)

(defun c:7 ()
(command "_view" "_r" "7")
)

(defun c:8 ()
(command "_view" "_r" "8")
)

(defun c:9 ()
(command "_view" "_r" "9")
)

(defun c:0 ()
(command "_view" "_r" "0")
)

(defun c:s1 ()
(command "_view" "_s" "1")
)

(defun c:s2 ()
(command "_view" "_s" "2")
)

(defun c:s3 ()
(command "_view" "_s" "3")
)

(defun c:s4 ()
(command "_view" "_s" "4")
)

(defun c:s5 ()
(command "_view" "_s" "5")
)

(defun c:s6 ()
(command "_view" "_s" "6")
)

(defun c:s7 ()
(command "_view" "_s" "7")
)

(defun c:s8 ()
(command "_view" "_s" "8")
)

(defun c:s9 ()
(command "_view" "_s" "9")
)

(defun c:s0 ()
(command "_view" "_s" "0")
)
