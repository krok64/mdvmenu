;;; Utils for AutoCAD 14-2014
;;; Обертки для вызовов vba функций
;;; (C) Milkov Dmitry, 2001-2016
;;; <Last edition 22.09.16>

(defun c:vbDrawpolka () (command "-vbarun" "DrawPolka"))
(defun c:vbTees () (command "-vbarun" "Tees"))
(defun c:vbCap () (command "-vbarun" "Cap"))
(defun c:vbBend () (command "-vbarun" "Bend"))
(defun c:vbReducer () (command "-vbarun" "Reducer"))
(defun c:vbPrintA4 () (command "-vbarun" "PlotA4"))
(defun c:vbPrintA4prev () (command "-vbarun" "TestPlotA4"))
(defun c:vbPrintA3 () (command "-vbarun" "PlotA3"))
(defun c:vbPrintA3prev () (command "-vbarun" "TestPlotA3"))
(defun c:vbTextAttCabel () (command "-vbarun" "TextAttCabel"))
(defun c:vbTextAttTP () (command "-vbarun" "TextAttTP"))
(defun c:vbTextVodValik () (command "-vbarun" "TextVodValik"))
(defun c:vbTextGlinPerem () (command "-vbarun" "TextGlinPerem"))
(defun c:vbTextGruntProezd () (command "-vbarun" "TextGruntProezd"))
(defun c:vbTextZashKoz () (command "-vbarun" "TextZashKoz"))
(defun c:vbTextZnakZakreplTrassGP () (command "-vbarun" "TextZnakZakreplTrassGP"))
(defun c:vbTextZnakGPVisDav () (command "-vbarun" "TextZnakGPVisDav"))
(defun c:vbTextZnakKondVisDav () (command "-vbarun" "TextZnakKondVisDav"))
(defun c:vbTextMarkerNakladki () (command "-vbarun" "TextMarkerNakladki"))
(defun c:vbTextNedeistvGPPodlDemont () (command "-vbarun" "TextNedeistvGPPodlDemont"))
(defun c:vbTextPlanirovkaPoverh () (command "-vbarun" "TextPlanirovkaPoverh"))
(defun c:vbTextPlitiPDN () (command "-vbarun" "TextPlitiPDN"))
(defun c:vbTextPK () (command "-vbarun" "TextPK"))
(defun c:vbTextPlakatOstorojnoGP () (command "-vbarun" "TextPlakatOstorojnoGP"))
(defun c:vbTextStolbikSign () (command "-vbarun" "TextStolbikSign"))
(defun c:vbTextSushVL () (command "-vbarun" "TextSushVL"))
(defun c:vbTextSushGP () (command "-vbarun" "TextSushGP"))
(defun c:vbTextSushCondP () (command "-vbarun" "TextSushCondP"))
(defun c:vbTextTrassaProectGP () (command "-vbarun" "TextTrassaProectGP"))
(defun c:vbTextTrassaProectKP () (command "-vbarun" "TextTrassaProectKP"))
(defun c:vbMarkLeaders () (command "-vbarun" "MarkLeaders"))
(defun c:vbUnMarkLeaders () (command "-vbarun" "UnMarkLeaders"))
(defun c:vbChange_Leader () (command "-vbarun" "Change_Leader"))
(defun c:vbDeepVolume () (command "-vbarun" "DeepVolume"))
(defun c:vbDimSumm () (command "-vbarun" "DimSumm"))
(defun c:vbDrawValik() (command "-vbarun" "DrawValic"))
(defun c:vbVRtoWord() (command "-vbarun" "VRtoWord"))
(defun c:vbSOtoWord() (command "-vbarun" "SOtoWord"))
(defun c:vbUKtoWord() (command "-vbarun" "UklonToWord"))
(defun c:vbUgPovToWord() (command "-vbarun" "UgPovToWord"))
(defun c:vbSetGOST() (command "-vbarun" "SetFont_GOST"))
(defun c:vbDrawLand() (command "-vbarun" "DrawLand"))
(defun c:vbimportvk() (command "-vbarun" "LoadDataVK"))
(defun c:vbmoveug() (command "-vbarun" "MoveUG"))
(defun c:vbkolodez() (command "-vbarun" "Kolodez"))
(defun c:vbSkv() (command "-vbarun" "SkvVK"))
(defun c:vbFutlar() (command "-vbarun" "Futlar"))
(defun c:vbtextadde() (command "-vbarun" "AddTextend"))
(defun c:3Dtruba() (command "-vbarun" "Draw3Pipe"))
(defun c:3Dkran() (command "-vbarun" "Draw3Kran"))
(defun c:3Dotvod() (command "-vbarun" "Draw3Otvod"))
(defun c:3Dperehod() (command "-vbarun" "Draw3Pereh"))
(defun c:3Dtroy() (command "-vbarun" "Draw3Troy"))
(defun c:3Dzagl() (command "-vbarun" "Draw3Zagl"))
(defun c:vbacadtoexcel() (command "-vbarun" "AcadToExcel"))
(defun c:vbsavecloseall() (command "-vbarun" "SavaAndCloseAll"))
(defun c:vbDrawLeader() (command "-vbarun" "TextLead"))
(defun c:vbLeaderImport() (command "-vbarun" "ImportLeadersFromExcel"))
(defun c:vbText2MText() (command "-vbarun" "Text2MText"))
